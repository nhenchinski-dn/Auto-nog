// validate-yangs ignore-lib
module dn-events-system {
  namespace "http://drivenets.com/ns/yang/dn-events-system";
  prefix dn-events-system;

  import dn-events-extensions {
    prefix dn-events-extensions;
  }

  organization
    "DRIVENETS LTD";
  contact
    "DRIVENETS Customer Service <mailto:support@drivenets.com>";
  description
    "This module contains a collection of YANG definitions for
     managing DRIVENETS Interface events";

  revision 2018-06-20 {
    description
      "Initial revision";
  }

  typedef ieeefloat32 {
    type binary {
      length "4";
    }
    description
      "An IEEE 32-bit floating point number. The format of this number is of the form:
       1-bit  sign
       8-bit  exponent
       23-bit fraction
       The floating point value is calculated using:
       (-1)**S * 2**(Exponent-127) * (1+Fraction)";
  }

  // NCE events

  notification NCP_STATE_CHANGE {
    description
      "The NCP has changed its state.";
    dn-events-extensions:event-severity-level "Info";
    dn-events-extensions:event-message-string "NCP {ncp-id} state has changed from {old-state} to {new-state}";
    dn-events-extensions:event-corrective-action-string "This is informational, no corrective action required.";
    dn-events-extensions:event-trigger-component-string "Cluster Manager";
    dn-events-extensions:event-group "System";
    dn-events-extensions:event-snmp-trap-name "dnNcpOperStatusChange";
    dn-events-extensions:event-snmp-trap-oid ".1.3.6.1.4.1.49739.2.6.0.4";
    dn-events-extensions:event-snmp-trap-vars "dnNcpOperStatus.CONVERTIDX(ncpID,{ncp-id}) CONVERT ncpOpStC {new-state}; dnNcpOperStatusLastChangeTime.CONVERTIDX(ncpID,{ncp-id}) {sys-uptime}";
    leaf old-state {
      type string;
      description
        "NCP old state";
    }
    leaf new-state {
      type string;
      description
        "NCP new state";
    }
    leaf ncp-id {
      type uint16;
      description
        "NCP ID";
    }
    leaf sys-uptime {
      type uint32;
      description
        "sysUpTime value at the moment of the state change";
    }
  }

  notification NCP_UPGRADE_STATE_CHANGE {
    description
      "The NCP is currently in baseos/firmware upgrade and it has changed its state.";
    dn-events-extensions:event-severity-level "Info";
    dn-events-extensions:event-message-string "NCP with serial number {ncp-serial-number} has changed it upgrade state from {old-state} to {new-state}";
    dn-events-extensions:event-corrective-action-string "This is informational, no corrective action required.";
    dn-events-extensions:event-trigger-component-string "Cluster Manager";
    dn-events-extensions:event-group "System";
    leaf old-state {
      type string;
      description
        "NCP old state and sub-state";
    }
    leaf new-state {
      type string;
      description
        "NCP new state and sub-state";
    }
    leaf ncp-serial-number {
      type string;
      description
        "NCP serial nunmber";
    }
  }

  notification NCP_CONFIG {
    description
      "A user has updated the NCP configuration.";
    dn-events-extensions:event-severity-level "Info";
    dn-events-extensions:event-message-string "User {user-name} has {action} NCP {ncp-id} model {model} configuration";
    dn-events-extensions:event-corrective-action-string "This is informational, no corrective action required.";
    dn-events-extensions:event-trigger-component-string "Transaction-manager";
    dn-events-extensions:event-group "System";
    leaf action {
      type string;
      description
        "NCP configuration action (added/removed)";
    }
    leaf model {
      type string;
      description
        "NCP configured model";
    }
    leaf ncp-id {
      type uint16;
      description
        "NCP ID";
    }
    leaf user-name {
      type string;
      description
        "System user-name";
    }
  }

  notification NCP_STATE_CHANGE_FAILED {
    description
      "The NCP failed due to an internal error, misconfiguration, or the NCP was reset.";
    dn-events-extensions:event-severity-level "Critical";
    dn-events-extensions:event-message-string "NCP {ncp-id} state has changed from {old-state} to {new-state}";
    dn-events-extensions:event-corrective-action-string "Contact Customer Support.";
    dn-events-extensions:event-trigger-component-string "WB Agent";
    dn-events-extensions:event-group "System";
    dn-events-extensions:event-snmp-trap-name "dnNcpOperStatusChange";
    dn-events-extensions:event-snmp-trap-oid ".1.3.6.1.4.1.49739.2.6.0.4";
    dn-events-extensions:event-snmp-trap-vars "dnNcpOperStatus.CONVERTIDX(ncpID,{ncp-id}) CONVERT ncpOpStC {new-state}; dnNcpOperStatusLastChangeTime.CONVERTIDX(ncpID,{ncp-id}) {sys-uptime}";
    leaf old-state {
      type string;
      description
        "NCP old state";
    }
    leaf new-state {
      type string;
      description
        "NCP new state";
    }
    leaf ncp-id {
      type uint16;
      description
        "NCP ID";
    }
    leaf sys-uptime {
      type uint32;
      description
        "sysUpTime value at the moment of the state change";
    }
  }

  notification NCP_STATE_CHANGE_DISCONNECTED {
    description
      "The NCP is disconnected.";
    dn-events-extensions:event-severity-level "Warning";
    dn-events-extensions:event-message-string "NCP {ncp-id} state has changed from {old-state} to {new-state}";
    dn-events-extensions:event-corrective-action-string "Contact Customer Support.";
    dn-events-extensions:event-trigger-component-string "WB Agent";
    dn-events-extensions:event-group "System";
    dn-events-extensions:event-snmp-trap-name "dnNcpOperStatusChange";
    dn-events-extensions:event-snmp-trap-oid ".1.3.6.1.4.1.49739.2.6.0.4";
    dn-events-extensions:event-snmp-trap-vars "dnNcpOperStatus.CONVERTIDX(ncpID,{ncp-id}) CONVERT ncpOpStC {new-state}; dnNcpOperStatusLastChangeTime.CONVERTIDX(ncpID,{ncp-id}) {sys-uptime}";
    leaf old-state {
      type string;
      description
        "NCP old state";
    }
    leaf new-state {
      type string;
      description
        "NCP new state";
    }
    leaf ncp-id {
      type uint16;
      description
        "NCP ID";
    }
    leaf sys-uptime {
      type uint32;
      description
        "sysUpTime value at the moment of the state change";
    }
  }

  notification NCP_ADMIN_STATE_CONFIG {
    description
      "The user has changed the indicated NCP admin-state.";
    dn-events-extensions:event-severity-level "Info";
    dn-events-extensions:event-message-string "User {user-name} has changed NCP {ncp-id} admin-state to {new-state}";
    dn-events-extensions:event-corrective-action-string "This is informational, no corrective action required.";
    dn-events-extensions:event-trigger-component-string "Transaction-manager";
    dn-events-extensions:event-group "System";
    leaf new-state {
      type string;
      description
        "NCP new state";
    }
    leaf ncp-id {
      type uint16;
      description
        "NCP ID";
    }
    leaf user-name {
      type string;
      description
        "System user-name";
    }
  }

  notification NCP_TO_NCP_REACHABILITY_STATE_UP {
    description
      "The NCP has reachability to the listed NCP neighbor.";
    dn-events-extensions:event-severity-level "Info";
    dn-events-extensions:event-message-string "NCP {ncp-id} has reachability to neighbor NCP {neighbor-ncp-id}";
    dn-events-extensions:event-corrective-action-string "This is informational, no corrective action required.";
    dn-events-extensions:event-trigger-component-string "Cluster Manager";
    dn-events-extensions:event-group "System";
    leaf ncp-id {
      type uint16;
      description
        "NCP ID";
    }
    leaf neighbor-ncp-id {
      type uint16;
      description
        "NCP ID";
    }
  }

  notification NCP_TO_NCP_REACHABILITY_STATE_DOWN {
    description
      "The NCP has no reachability with the listed NCP neighbor.";
    dn-events-extensions:event-severity-level "Critical";
    dn-events-extensions:event-message-string "NCP {ncp-id} lost reachability to neighbor NCP {neighbor-ncp-id}";
    dn-events-extensions:event-corrective-action-string "Check the connectivity between the nodes.";
    dn-events-extensions:event-trigger-component-string "Cluster Manager";
    dn-events-extensions:event-group "System";
    leaf ncp-id {
      type uint16;
      description
        "NCP ID";
    }
    leaf neighbor-ncp-id {
      type uint16;
      description
        "NCP ID";
    }
  }

  notification NCF_TO_NCP_CONNECTIVITY_STATE_UP {
    description
      "The NCF has connectivity to the listed NCP neighbor.";
    dn-events-extensions:event-severity-level "Info";
    dn-events-extensions:event-message-string "NCF {ncf-id} has connectivity to neighbor NCP {neighbor-ncp-id}";
    dn-events-extensions:event-corrective-action-string "This is informational, no corrective action required.";
    dn-events-extensions:event-trigger-component-string "Cluster Manager";
    dn-events-extensions:event-group "System";
    leaf ncf-id {
      type uint16;
      description
        "NCF ID";
    }
    leaf neighbor-ncp-id {
      type uint16;
      description
        "NCP ID";
    }
  }

  notification NCF_TO_NCP_CONNECTIVITY_STATE_DOWN {
    description
      "The NCF has no connectivity with the listed NCP neighbor.";
    dn-events-extensions:event-severity-level "Critical";
    dn-events-extensions:event-message-string "NCF {ncf-id} lost connectivity to neighbor NCP {neighbor-ncp-id}";
    dn-events-extensions:event-corrective-action-string "Check the connectivity between the nodes.";
    dn-events-extensions:event-trigger-component-string "Cluster Manager";
    dn-events-extensions:event-group "System";
    leaf ncf-id {
      type uint16;
      description
        "NCF ID";
    }
    leaf neighbor-ncp-id {
      type uint16;
      description
        "NCP ID";
    }
  }

  notification NCP_TO_NCF_CONNECTIVITY_STATE_UP {
    description
      "The NCP has connectivity to the listed NCF neighbor.";
    dn-events-extensions:event-severity-level "Info";
    dn-events-extensions:event-message-string "NCP {ncp-id} has connectivity to neighbor NCF {neighbor-ncf-id}";
    dn-events-extensions:event-corrective-action-string "This is informational, no corrective action required.";
    dn-events-extensions:event-trigger-component-string "Cluster Manager";
    dn-events-extensions:event-group "System";
    leaf ncp-id {
      type uint16;
      description
        "NCP ID";
    }
    leaf neighbor-ncf-id {
      type uint16;
      description
        "NCF ID";
    }
  }

  notification NCP_TO_NCF_CONNECTIVITY_STATE_DOWN {
    description
      "The NCP has no connectivity with the listed NCF neighbor.";
    dn-events-extensions:event-severity-level "Critical";
    dn-events-extensions:event-message-string "NCP {ncp-id} lost connectivity to neighbor NCF {neighbor-ncf-id}";
    dn-events-extensions:event-corrective-action-string "Check the connectivity between the nodes.";
    dn-events-extensions:event-trigger-component-string "Cluster Manager";
    dn-events-extensions:event-group "System";
    leaf ncp-id {
      type uint16;
      description
        "NCP ID";
    }
    leaf neighbor-ncf-id {
      type uint16;
      description
        "NCF ID";
    }
  }

  notification NCF_TO_NCF_CONNECTIVITY_STATE_UP {
    description
      "The NCF has connectivity to the listed multi-stage fabric NCF neighbor.";
    dn-events-extensions:event-severity-level "Info";
    dn-events-extensions:event-message-string "NCF {ncf-id} has connectivity to neighbor NCF {neighbor-ncf-id}";
    dn-events-extensions:event-corrective-action-string "This is informational, no corrective action required.";
    dn-events-extensions:event-trigger-component-string "Cluster Manager";
    dn-events-extensions:event-group "System";
    leaf ncf-id {
      type uint16;
      description
        "NCF ID";
    }
    leaf neighbor-ncf-id {
      type uint16;
      description
        "NCF ID";
    }
  }

  notification NCF_TO_NCF_CONNECTIVITY_STATE_DOWN {
    description
      "The NCF has no connectivity with the listed multi-stage fabric NCF neighbor.";
    dn-events-extensions:event-severity-level "Critical";
    dn-events-extensions:event-message-string "NCF {ncf-id} lost connectivity to neighbor NCF {neighbor-ncf-id}";
    dn-events-extensions:event-corrective-action-string "Check the connectivity between the nodes.";
    dn-events-extensions:event-trigger-component-string "Cluster Manager";
    dn-events-extensions:event-group "System";
    leaf ncf-id {
      type uint16;
      description
        "NCF ID";
    }
    leaf neighbor-ncf-id {
      type uint16;
      description
        "NCF ID";
    }
  }

  notification NCF_DYNAMIC_FABRIC_STATE_INITIALIZED {
    description
      "Fabric connectivity state has been initialized successfully on the listed NCF node as part of system initialization flow when dynamic fabric connectivity is enabled.";
    dn-events-extensions:event-severity-level "Notice";
    dn-events-extensions:event-message-string "Fabric connectivity state has been initialized successfully on NCF {ncf-id} interface {if-name}";
    dn-events-extensions:event-corrective-action-string "This is informational, no corrective action required.";
    dn-events-extensions:event-trigger-component-string "Cluster Manager";
    dn-events-extensions:event-group "System";
    leaf ncf-id {
      type uint16;
      description
        "NCF ID";
    }
    leaf if-name {
      type string;
      description
        "NCF fabric interface";
    }
  }

  notification NCF_FABRIC_CONNECTIVITY_CHANGED {
    description
      "Fabric connectivity configuration has been changed on the listed NCF node.";
    dn-events-extensions:event-severity-level "Notice";
    dn-events-extensions:event-message-string "Fabric connectivity configuration changed for NCF {ncf-id} interface {if-name} connected to NCP {ncp-id} interface {if-name-dest}";
    dn-events-extensions:event-corrective-action-string "This is informational, no corrective action required.";
    dn-events-extensions:event-trigger-component-string "Cluster Manager";
    dn-events-extensions:event-group "System";
    leaf ncf-id {
      type uint16;
      description
        "NCF ID";
    }
    leaf if-name {
      type string;
      description
        "NCF fabric interface";
    }
    leaf ncp-id {
      type uint16;
      description
        "NCP ID";
    }
    leaf if-name-dest {
      type string;
      description
        "NCP fabric interface";
    }
  }

  notification MULTI_STAGE_FABRIC_CONNECTIVITY_ERROR {
    description
      "Bad connection detected between two nodes in the multi-stage fabric cluster.";
    dn-events-extensions:event-severity-level "Critical";
    dn-events-extensions:event-message-string "Interface {if-name} connected to {if-name-dest}.";
    dn-events-extensions:event-corrective-action-string "Check the connectivity between the nodes.";
    dn-events-extensions:event-trigger-component-string "Cluster Manager";
    dn-events-extensions:event-group "System";
    leaf if-name {
      type string;
      description
        "Interface name";
    }
    leaf if-name-dest {
      type string;
      description
        "Interface name";
    }
  }

  notification NCP_COLD_RESTART_USER {
    description
      "The user indicated performed a cold restart on the NCP.";
    dn-events-extensions:event-severity-level "Info";
    dn-events-extensions:event-message-string "User {user-name} performed cold restart on NCP {ncp-id}";
    dn-events-extensions:event-corrective-action-string "This is informational, no corrective action required.";
    dn-events-extensions:event-trigger-component-string "Transaction-manager";
    dn-events-extensions:event-group "System";
    leaf ncp-id {
      type uint16;
      description
        "NCP ID";
    }
    leaf user-name {
      type string;
      description
        "System user-name";
    }
  }

  notification NCC_COLD_RESTART_USER {
    description
      "The user indicated performed a cold restart on the NCC.";
    dn-events-extensions:event-severity-level "Info";
    dn-events-extensions:event-message-string "User {user-name} performed cold restart on NCC {ncc-id}";
    dn-events-extensions:event-corrective-action-string "This is informational, no corrective action required.";
    dn-events-extensions:event-trigger-component-string "Transaction-manager";
    dn-events-extensions:event-group "System";
    leaf ncc-id {
      type uint16;
      description
        "NCC ID";
    }
    leaf user-name {
      type string;
      description
        "System user-name";
    }
  }

  notification NCF_COLD_RESTART_USER {
    description
      "The user indicated performed a cold restart on the NCF.";
    dn-events-extensions:event-severity-level "Info";
    dn-events-extensions:event-message-string "User {user-name} performed cold restart on NCF {ncf-id}";
    dn-events-extensions:event-corrective-action-string "This is informational, no corrective action required.";
    dn-events-extensions:event-trigger-component-string "Transaction-manager";
    dn-events-extensions:event-group "System";
    leaf ncf-id {
      type uint16;
      description
        "NCF ID";
    }
    leaf user-name {
      type string;
      description
        "System user-name";
    }
  }

  notification NCM_COLD_RESTART_USER {
    description
      "The user indicated performed a cold restart on the NCM.";
    dn-events-extensions:event-severity-level "Info";
    dn-events-extensions:event-message-string "User {user-name} performed cold restart on NCM {ncm-id}";
    dn-events-extensions:event-corrective-action-string "This is informational, no corrective action required.";
    dn-events-extensions:event-trigger-component-string "Transaction-manager";
    dn-events-extensions:event-group "System";
    leaf ncm-id {
      type string;
      description
        "NCM ID";
    }
    leaf user-name {
      type string;
      description
        "System user-name";
    }
  }

  notification NCP_WARM_RESTART_USER {
    description
      "The user indicated performed a warm restart on the NCP.";
    dn-events-extensions:event-severity-level "Info";
    dn-events-extensions:event-message-string "User {user-name} performed warm restart on NCP {ncp-id}";
    dn-events-extensions:event-corrective-action-string "This is informational, no corrective action required.";
    dn-events-extensions:event-trigger-component-string "Transaction-manager";
    dn-events-extensions:event-group "System";
    leaf ncp-id {
      type uint16;
      description
        "NCP ID";
    }
    leaf user-name {
      type string;
      description
        "System user-name";
    }
  }

  notification NCC_WARM_RESTART_USER {
    description
      "The user indicated performed a warm restart on the NCC.";
    dn-events-extensions:event-severity-level "Info";
    dn-events-extensions:event-message-string "User {user-name} performed warm restart on NCC {ncc-id}";
    dn-events-extensions:event-corrective-action-string "This is informational, no corrective action required.";
    dn-events-extensions:event-trigger-component-string "Transaction-manager";
    dn-events-extensions:event-group "System";
    leaf ncc-id {
      type uint16;
      description
        "NCC ID";
    }
    leaf user-name {
      type string;
      description
        "System user-name";
    }
  }

  notification NCF_WARM_RESTART_USER {
    description
      "The user indicated performed a warm restart on the NCF.";
    dn-events-extensions:event-severity-level "Info";
    dn-events-extensions:event-message-string "User {user-name} performed warm restart on NCF {ncf-id}";
    dn-events-extensions:event-corrective-action-string "This is informational, no corrective action required.";
    dn-events-extensions:event-trigger-component-string "Transaction-manager";
    dn-events-extensions:event-group "System";
    leaf ncf-id {
      type uint16;
      description
        "NCF ID";
    }
    leaf user-name {
      type string;
      description
        "System user-name";
    }
  }

  notification NCP_ID_ASSIGNED {
    description
      "The Element Manager released its ID from LLDP and assigned an ID to the NCP node.";
    dn-events-extensions:event-severity-level "Info";
    dn-events-extensions:event-message-string "NCP {ncp-id} serial number {node-serial-number} ID is assigned. Identified neighbor interfaces: {first-neighbor-interface-name}, {second-neighbor-interface-name}";
    dn-events-extensions:event-corrective-action-string "This is informational, no corrective action required.";
    dn-events-extensions:event-trigger-component-string "Element Manager";
    dn-events-extensions:event-group "System";
    leaf ncp-id {
      type uint16;
      description
        "NCP ID";
    }
    leaf node-serial-number {
      type string;
      description
        "NCP node serial number";
    }
    leaf first-neighbor-interface-name {
      type string;
      description
        "NCM interface name";
    }
    leaf second-neighbor-interface-name {
      type string;
      description
        "NCM interface name";
    }
  }

  notification NCP_ID_COLLISION_STOP {
    description
      "During startup the Element Manager could not determine which ID to assign due to a conflict. This NCP node has stopped at the state, initializing.";
    dn-events-extensions:event-severity-level "Error";
    dn-events-extensions:event-message-string "NCP serial number {node-serial-number} has stopped initializing due to connection conflict. Identified neighbor interfaces: {first-neighbor-interface-name}, {second-neighbor-interface-name}";
    dn-events-extensions:event-corrective-action-string "Fix NCP to NCM physical connectivity according the connectivity matrix.";
    dn-events-extensions:event-trigger-component-string "Element Manager";
    dn-events-extensions:event-group "System";
    leaf node-serial-number {
      type string;
      description
        "NCP node serial number";
    }
    leaf first-neighbor-interface-name {
      type string;
      description
        "NCM interface name";
    }
    leaf second-neighbor-interface-name {
      type string;
      description
        "NCM interface name";
    }
  }

  notification NCP_ID_COLLISION_RESET {
    description
      "After the Element Manager has assigned an ID to an NCP node a user connected the control interfaces causing an ID conflict. This will cause the node to reset.";
    dn-events-extensions:event-severity-level "Error";
    dn-events-extensions:event-message-string "NCP ID {ncp-id} serial number {node-serial-number} will reset due to connectivity change. Identified neighbor interfaces: {first-neighbor-interface-name}, {second-neighbor-interface-name}";
    dn-events-extensions:event-corrective-action-string "Fix NCP to NCM physical connectivity according the connectivity matrix.";
    dn-events-extensions:event-trigger-component-string "Element Manager";
    dn-events-extensions:event-group "System";
    leaf ncp-id {
      type uint16;
      description
        "NCP ID before conflict";
    }
    leaf node-serial-number {
      type string;
      description
        "NCP node serial number";
    }
    leaf first-neighbor-interface-name {
      type string;
      description
        "NCM interface name";
    }
    leaf second-neighbor-interface-name {
      type string;
      description
        "NCM interface name";
    }
  }

  notification NCF_STATE_CHANGE {
    description
      "The NCF has changed its state.";
    dn-events-extensions:event-severity-level "Info";
    dn-events-extensions:event-message-string "NCF {ncf-id} state has changed from {old-state} to {new-state}";
    dn-events-extensions:event-corrective-action-string "This is informational, no corrective action required.";
    dn-events-extensions:event-trigger-component-string "WB Agent";
    dn-events-extensions:event-group "System";
    dn-events-extensions:event-snmp-trap-name "dnNcfOperStatusChange";
    dn-events-extensions:event-snmp-trap-oid ".1.3.6.1.4.1.49739.2.6.0.5";
    dn-events-extensions:event-snmp-trap-vars "dnNcfOperStatus.CONVERTIDX(ncfID,{ncf-id}) CONVERT ncfOpStC {new-state}; dnNcfOperStatusLastChangeTime.CONVERTIDX(ncfID,{ncf-id}) {sys-uptime}";
    leaf old-state {
      type string;
      description
        "NCF old state";
    }
    leaf new-state {
      type string;
      description
        "NCF new state";
    }
    leaf ncf-id {
      type uint16;
      description
        "NCF ID";
    }
    leaf sys-uptime {
      type uint32;
      description
        "sysUpTime value at the moment of the state change";
    }
  }

  notification NCF_UPGRADE_STATE_CHANGE {
    description
      "The NCF is currently in baseos/firmware upgrade and it has changed its state.";
    dn-events-extensions:event-severity-level "Info";
    dn-events-extensions:event-message-string "NCF with serial number {ncf-serial-number} has changed it upgrade state from {old-state} to {new-state}";
    dn-events-extensions:event-corrective-action-string "This is informational, no corrective action required.";
    dn-events-extensions:event-trigger-component-string "WB Agent";
    dn-events-extensions:event-group "System";
    leaf old-state {
      type string;
      description
        "NCF old state and sub-state";
    }
    leaf new-state {
      type string;
      description
        "NCF new state and sub-state";
    }
    leaf ncf-serial-number {
      type string;
      description
        "NCF serial nunmber";
    }
  }

  notification NCF_STATE_CHANGE_FAILED {
    description
      "The NCF failed due to an internal error, misconfiguration, or the NCF was reset.";
    dn-events-extensions:event-severity-level "Critical";
    dn-events-extensions:event-message-string "NCF {ncf-id} state has changed from {old-state} to {new-state}";
    dn-events-extensions:event-corrective-action-string "Contact Customer Support.";
    dn-events-extensions:event-trigger-component-string "WB Agent";
    dn-events-extensions:event-group "System";
    dn-events-extensions:event-snmp-trap-name "dnNcfOperStatusChange";
    dn-events-extensions:event-snmp-trap-oid ".1.3.6.1.4.1.49739.2.6.0.5";
    dn-events-extensions:event-snmp-trap-vars "dnNcfOperStatus.CONVERTIDX(ncfID,{ncf-id}) CONVERT ncfOpStC {new-state}; dnNcfOperStatusLastChangeTime.CONVERTIDX(ncfID,{ncf-id}) {sys-uptime}";
    leaf old-state {
      type string;
      description
        "NCF old state";
    }
    leaf new-state {
      type string;
      description
        "NCF new state";
    }
    leaf ncf-id {
      type uint16;
      description
        "NCF ID";
    }
    leaf sys-uptime {
      type uint32;
      description
        "sysUpTime value at the moment of the state change";
    }
  }

  notification NCF_STATE_CHANGE_DISCONNECTED {
    description
      "The NCF is disconnected.";
    dn-events-extensions:event-severity-level "Warning";
    dn-events-extensions:event-message-string "NCF {ncf-id} state has changed from {old-state} to {new-state}";
    dn-events-extensions:event-corrective-action-string "Contact Customer Support.";
    dn-events-extensions:event-trigger-component-string "WB Agent";
    dn-events-extensions:event-group "System";
    dn-events-extensions:event-snmp-trap-name "dnNcfOperStatusChange";
    dn-events-extensions:event-snmp-trap-oid ".1.3.6.1.4.1.49739.2.6.0.5";
    dn-events-extensions:event-snmp-trap-vars "dnNcfOperStatus.CONVERTIDX(ncfID,{ncf-id}) CONVERT ncfOpStC {new-state}; dnNcfOperStatusLastChangeTime.CONVERTIDX(ncfID,{ncf-id}) {sys-uptime}";
    leaf old-state {
      type string;
      description
        "NCF old state";
    }
    leaf new-state {
      type string;
      description
        "NCF new state";
    }
    leaf ncf-id {
      type uint16;
      description
        "NCF ID";
    }
    leaf sys-uptime {
      type uint32;
      description
        "sysUpTime value at the moment of the state change";
    }
  }

  notification NCF_ADMIN_STATE_CONFIG {
    description
      "The user has changed the indicated NCF admin-state.";
    dn-events-extensions:event-severity-level "Info";
    dn-events-extensions:event-message-string "User {user-name} has changed NCF {ncf-id} admin-state to {new-state}";
    dn-events-extensions:event-corrective-action-string "This is informational, no corrective action required.";
    dn-events-extensions:event-trigger-component-string "Transaction-manager";
    dn-events-extensions:event-group "System";
    leaf new-state {
      type string;
      description
        "NCF new state";
    }
    leaf ncf-id {
      type uint16;
      description
        "NCF ID";
    }
    leaf user-name {
      type string;
      description
        "System user-name";
    }
  }

  notification NCF_ID_ASSIGNED {
    description
      "The Element Manager released its ID from LLDP and assigned an ID to the NCF node.";
    dn-events-extensions:event-severity-level "Info";
    dn-events-extensions:event-message-string "NCF {ncf-id} serial number {node-serial-number} ID has assigned. Identified neighbor interfaces: {first-neighbor-interface-name}, {second-neighbor-interface-name}";
    dn-events-extensions:event-corrective-action-string "This is informational, no corrective action required.";
    dn-events-extensions:event-trigger-component-string "Element Manager";
    dn-events-extensions:event-group "System";
    leaf ncf-id {
      type uint16;
      description
        "NCF ID";
    }
    leaf node-serial-number {
      type string;
      description
        "NCF node serial number";
    }
    leaf first-neighbor-interface-name {
      type string;
      description
        "NCM interface name";
    }
    leaf second-neighbor-interface-name {
      type string;
      description
        "NCM interface name";
    }
  }

  notification NCF_ID_COLLISION_STOP {
    description
      "During startup the Element Manager could not determine which ID to assign due to a conflict. This NCF node has stopped at the state, initializing.";
    dn-events-extensions:event-severity-level "Error";
    dn-events-extensions:event-message-string "NCF serial number {node-serial-number} has stopped initializing due to connection conflict. Identified neighbor interfaces: {first-neighbor-interface-name}, {second-neighbor-interface-name}";
    dn-events-extensions:event-corrective-action-string "Fix NCF to NCM physical connectivity according the connectivity matrix.";
    dn-events-extensions:event-trigger-component-string "Element Manager";
    dn-events-extensions:event-group "System";
    leaf node-serial-number {
      type string;
      description
        "NCF node serial number";
    }
    leaf first-neighbor-interface-name {
      type string;
      description
        "NCM interface name";
    }
    leaf second-neighbor-interface-name {
      type string;
      description
        "NCM interface name";
    }
  }

  notification NCF_ID_COLLISION_RESET {
    description
      "After the Element Manager has assigned an ID to an NCF node a user connected the control interfaces causing an ID conflict. This will cause the node to reset.";
    dn-events-extensions:event-severity-level "Error";
    dn-events-extensions:event-message-string "NCF ID {ncf-id} serial number {node-serial-number} will reset due to connectivity change. Identified neighbor interfaces: {first-neighbor-interface-name}, {second-neighbor-interface-name}";
    dn-events-extensions:event-corrective-action-string "Fix NCF to NCM physical connectivity according the connectivity matrix.";
    dn-events-extensions:event-trigger-component-string "Element Manager";
    dn-events-extensions:event-group "System";
    leaf ncf-id {
      type uint16;
      description
        "NCF ID before conflict";
    }
    leaf node-serial-number {
      type string;
      description
        "NCF node serial number";
    }
    leaf first-neighbor-interface-name {
      type string;
      description
        "NCM interface name";
    }
    leaf second-neighbor-interface-name {
      type string;
      description
        "NCM interface name";
    }
  }

  notification NCC_STATE_CHANGE_FAILED {
    description
      "The NCC has failed due to an internal error.";
    dn-events-extensions:event-severity-level "Critical";
    dn-events-extensions:event-message-string "NCC {ncc-id} state has changed from {old-state} to {new-state}";
    dn-events-extensions:event-corrective-action-string "Contact Customer Support.";
    dn-events-extensions:event-trigger-component-string "HA-manager";
    dn-events-extensions:event-group "System";
    dn-events-extensions:event-snmp-trap-name "dnNccOperStatusChange";
    dn-events-extensions:event-snmp-trap-oid ".1.3.6.1.4.1.49739.2.6.0.6";
    dn-events-extensions:event-snmp-trap-vars "dnNccOperStatus.CONVERTIDX(nccID,{ncc-id}) CONVERT nccOpStC {new-state}; dnNccOperStatusLastChangeTime.CONVERTIDX(nccID,{ncc-id}) {sys-uptime}";
    leaf old-state {
      type string;
      description
        "NCC old state";
    }
    leaf new-state {
      type string;
      description
        "NCC new state";
    }
    leaf ncc-id {
      type uint16;
      description
        "NCC ID";
    }
    leaf sys-uptime {
      type uint32;
      description
        "sysUpTime value at the moment of the state change";
    }
  }

  notification NCC_STATE_CHANGE {
    description
      "The NCC has changed its state.";
    dn-events-extensions:event-severity-level "Info";
    dn-events-extensions:event-message-string "NCC {ncc-id} state has changed from {old-state} to {new-state}";
    dn-events-extensions:event-corrective-action-string "No corrective action.";
    dn-events-extensions:event-trigger-component-string "HA-manager";
    dn-events-extensions:event-group "System";
    dn-events-extensions:event-snmp-trap-name "dnNccOperStatusChange";
    dn-events-extensions:event-snmp-trap-oid ".1.3.6.1.4.1.49739.2.6.0.6";
    dn-events-extensions:event-snmp-trap-vars "dnNccOperStatus.CONVERTIDX(nccID,{ncc-id}) CONVERT nccOpStC {new-state}; dnNccOperStatusLastChangeTime.CONVERTIDX(nccID,{ncc-id}) {sys-uptime}";
    leaf old-state {
      type string;
      description
        "NCC old state";
    }
    leaf new-state {
      type string;
      description
        "NCC new state";
    }
    leaf ncc-id {
      type uint16;
      description
        "NCC ID";
    }
    leaf sys-uptime {
      type uint32;
      description
        "sysUpTime value at the moment of the state change";
    }
  }

  notification NCC_STATE_CHANGE_DISCONNECTED {
    description
      "The NCC is disconnected.";
    dn-events-extensions:event-severity-level "Warning";
    dn-events-extensions:event-message-string "NCC {ncc-id} state has changed from {old-state} to {new-state}";
    dn-events-extensions:event-corrective-action-string "Contact Customer Support.";
    dn-events-extensions:event-trigger-component-string "HA-manager";
    dn-events-extensions:event-group "System";
    dn-events-extensions:event-snmp-trap-name "dnNccOperStatusChange";
    dn-events-extensions:event-snmp-trap-oid ".1.3.6.1.4.1.49739.2.6.0.6";
    dn-events-extensions:event-snmp-trap-vars "dnNccOperStatus.CONVERTIDX(nccID,{ncc-id}) CONVERT nccOpStC {new-state}; dnNccOperStatusLastChangeTime.CONVERTIDX(nccID,{ncc-id}) {sys-uptime}";
    leaf old-state {
      type string;
      description
        "NCC old state";
    }
    leaf new-state {
      type string;
      description
        "NCC new state";
    }
    leaf ncc-id {
      type uint16;
      description
        "NCC ID";
    }
    leaf sys-uptime {
      type uint32;
      description
        "sysUpTime value at the moment of the state change";
    }
  }

  notification NCM_STATE_CHANGE {
    description
      "The NCM has changed its state.";
    dn-events-extensions:event-severity-level "Info";
    dn-events-extensions:event-message-string "NCM {ncm-id} state has changed from {old-state} to {new-state}";
    dn-events-extensions:event-corrective-action-string "This is informational, no corrective action required.";
    dn-events-extensions:event-trigger-component-string "Cluster Manager";
    dn-events-extensions:event-group "System";
    dn-events-extensions:event-snmp-trap-name "dnNcmOperStatusChange";
    dn-events-extensions:event-snmp-trap-oid ".1.3.6.1.4.1.49739.2.6.0.7";
    dn-events-extensions:event-snmp-trap-vars "dnNcmOperStatus.CONVERTIDX(ncmID,{ncm-id}) CONVERT ncmOpStC {new-state}; dnNcmOperStatusLastChangeTime.CONVERTIDX(ncmID,{ncm-id}) {sys-uptime}";
    leaf old-state {
      type string;
      description
        "NCM old state";
    }
    leaf new-state {
      type string;
      description
        "NCM new state";
    }
    leaf ncm-id {
      type string;
      description
        "NCM ID";
    }
    leaf sys-uptime {
      type uint32;
      description
        "sysUpTime value at the moment of the state change";
    }
  }

  notification NCM_STATE_CHANGE_FAILED {
    description
      "The NCM failed due to an internal error, misconfiguration, or the NCM was reset.";
    dn-events-extensions:event-severity-level "Critical";
    dn-events-extensions:event-message-string "NCM {ncm-id} state has changed from {old-state} to {new-state}";
    dn-events-extensions:event-corrective-action-string "Contact Customer Support.";
    dn-events-extensions:event-trigger-component-string "Cluster Manager";
    dn-events-extensions:event-group "System";
    dn-events-extensions:event-snmp-trap-name "dnNcmOperStatusChange";
    dn-events-extensions:event-snmp-trap-oid ".1.3.6.1.4.1.49739.2.6.0.7";
    dn-events-extensions:event-snmp-trap-vars "dnNcmOperStatus.CONVERTIDX(ncmID,{ncm-id}) CONVERT ncmOpStC {new-state}; dnNcmOperStatusLastChangeTime.CONVERTIDX(ncmID,{ncm-id}) {sys-uptime}";
    leaf old-state {
      type string;
      description
        "NCM old state";
    }
    leaf new-state {
      type string;
      description
        "NCM new state";
    }
    leaf ncm-id {
      type string;
      description
        "NCM ID";
    }
    leaf sys-uptime {
      type uint32;
      description
        "sysUpTime value at the moment of the state change";
    }
  }

  notification NCM_STATE_CHANGE_DISCONNECTED {
    description
      "The NCM is disconnected.";
    dn-events-extensions:event-severity-level "Warning";
    dn-events-extensions:event-message-string "NCM {ncm-id} state has changed from {old-state} to {new-state}";
    dn-events-extensions:event-corrective-action-string "Contact Customer Support.";
    dn-events-extensions:event-trigger-component-string "Cluster Manager";
    dn-events-extensions:event-group "System";
    dn-events-extensions:event-snmp-trap-name "dnNcmOperStatusChange";
    dn-events-extensions:event-snmp-trap-oid ".1.3.6.1.4.1.49739.2.6.0.7";
    dn-events-extensions:event-snmp-trap-vars "dnNcmOperStatus.CONVERTIDX(ncmID,{ncm-id}) CONVERT ncmOpStC {new-state}; dnNcmOperStatusLastChangeTime.CONVERTIDX(ncmID,{ncm-id}) {sys-uptime}";
    leaf old-state {
      type string;
      description
        "NCM old state";
    }
    leaf new-state {
      type string;
      description
        "NCM new state";
    }
    leaf ncm-id {
      type string;
      description
        "NCM ID";
    }
    leaf sys-uptime {
      type uint32;
      description
        "sysUpTime value at the moment of the state change";
    }
  }

  notification NCM_MISCONFIGURATION {
    description
      "The NCM configuration differs from the expected configuration. This can happen due to an internal error in the NCM.";
    dn-events-extensions:event-severity-level "Error";
    dn-events-extensions:event-message-string "Configuration on NCM {ncm-id} differs from the expected";
    dn-events-extensions:event-corrective-action-string "Run the command 'request system techsupport' and contact Customer Support.";
    dn-events-extensions:event-trigger-component-string "Cluster Manager";
    dn-events-extensions:event-group "System";
    leaf ncm-id {
      type string;
      description
        "NCM ID";
    }
  }

  notification NCM_PORT_LOOP_DETECTED {
    description
      "Bridge Protocol Data Units (BPDUs) were recieved on the listed NCM port indicating that a port loop was detected. The port has been blocked by the BPDU Guard.";
    dn-events-extensions:event-severity-level "Error";
    dn-events-extensions:event-message-string "Port loop detected in NCM {ncm-id}. Port {interface-name} has been blocked by BPDU Guard";
    dn-events-extensions:event-corrective-action-string "Recable the NCM interfaces to prevent port loops.";
    dn-events-extensions:event-trigger-component-string "Cluster Manager";
    dn-events-extensions:event-group "System";
    leaf ncm-id {
      type string;
      description
        "NCM ID";
    }
    leaf interface-name {
      type string;
      description
        "Blocked interface name";
    }
  }

  notification NCM_ID_ASSIGNED {
    description
      "The Cluster Manager released the NCM ID from LLDP and assigned an ID to the NCM node.";
    dn-events-extensions:event-severity-level "Info";
    dn-events-extensions:event-message-string "NCM {ncm-id} serial number {node-serial-number} ID is assigned. Identified neighbor interfaces: {first-neighbor-interface-name}, {second-neighbor-interface-name}";
    dn-events-extensions:event-corrective-action-string "This is informational, no corrective action required.";
    dn-events-extensions:event-trigger-component-string "Cluster Manager";
    dn-events-extensions:event-group "System";
    leaf ncm-id {
      type string;
      description
        "NCM ID";
    }
    leaf node-serial-number {
      type string;
      description
        "NCM node serial number";
    }
    leaf first-neighbor-interface-name {
      type string;
      description
        "Neighbor interface name";
    }
    leaf second-neighbor-interface-name {
      type string;
      description
        "Neighbor interface name";
    }
  }

  notification NCM_ID_COLLISION_ASSIGNED {
    description
      "The Cluster Manager has assigned an ID to the NCM node which conflicts with its LLDP neighbor.";
    dn-events-extensions:event-severity-level "Warning";
    dn-events-extensions:event-message-string "NCM {ncm-id} serial number {node-serial-number} ID is assigned with connection conflict. Identified neighbor interfaces: {first-neighbor-interface-name}, {second-neighbor-interface-name}";
    dn-events-extensions:event-corrective-action-string "Fix the NCM physical connectivity according to the connectivity matrix.";
    dn-events-extensions:event-trigger-component-string "Cluster Manager";
    dn-events-extensions:event-group "System";
    leaf ncm-id {
      type string;
      description
        "NCM ID";
    }
    leaf node-serial-number {
      type string;
      description
        "NCM node serial number";
    }
    leaf first-neighbor-interface-name {
      type string;
      description
        "Neighbor interface name";
    }
    leaf second-neighbor-interface-name {
      type string;
      description
        "Neighbor interface name";
    }
  }

  notification NCM_ID_COLLISION_RESET {
    description
      "The Cluster Manager has reset the ID on the NCM to its serial number due to a connection conflict.";
    dn-events-extensions:event-severity-level "Error";
    dn-events-extensions:event-message-string "NCM with serial number {node-serial-number} has reset the ID on the NCM to its serial number due to connection conflict. Identified neighbor interfaces: {first-neighbor-interface-name}, {second-neighbor-interface-name}";
    dn-events-extensions:event-corrective-action-string "Fix the NCM physical connectivity according to the connectivity matrix.";
    dn-events-extensions:event-trigger-component-string "Cluster Manager";
    dn-events-extensions:event-group "System";
    leaf node-serial-number {
      type string;
      description
        "NCM node serial number";
    }
    leaf first-neighbor-interface-name {
      type string;
      description
        "Neighbor interface name";
    }
    leaf second-neighbor-interface-name {
      type string;
      description
        "Neighbor interface name";
    }
  }

  notification SYSTEM_MINIMUM_FABRIC_THRESHOLD_BELOW {
    description
      "All of the NCPs in the cluster have changed state to system-down because the number of NCFs in the cluster is below the minimum number required. The minimum number of NCFs is displayed in the field 'configured-min-ncf-threshold'.";
    dn-events-extensions:event-severity-level "Critical";
    dn-events-extensions:event-message-string "Number of active NCF modules in the system is below the expected value ({configured-min-ncf-threshold}), the current number of active ncf modules is {active-ncf}";
    dn-events-extensions:event-corrective-action-string "Check the NCFs which are not in an 'up' state in the cluster.";
    dn-events-extensions:event-trigger-component-string "Cluster Manager";
    dn-events-extensions:event-group "System";
    leaf configured-min-ncf-threshold {
      type uint16;
      description
        "fabric-min-ncf configured value";
    }
    leaf active-ncf {
      type uint16;
      description
        "Current number of NCFs in the cluster with a state up";
    }
  }

  notification SYSTEM_MINIMUM_FABRIC_THRESHOLD_CLEARED {
    description
      "The number of active NCFs in the cluster is equal to or above the minimum number required for the cluster to function.";
    dn-events-extensions:event-severity-level "Info";
    dn-events-extensions:event-message-string "Number of active NCF modules in the system is equal or above the expected value ({configured-min-ncf-threshold}), the current number of active ncf modules is {active-ncf}";
    dn-events-extensions:event-corrective-action-string "This is informational, no corrective action required.";
    dn-events-extensions:event-trigger-component-string "Cluster Manager";
    dn-events-extensions:event-group "System";
    leaf configured-min-ncf-threshold {
      type uint16;
      description
        "fabric-min-ncf configured value";
    }
    leaf active-ncf {
      type uint16;
      description
        "Current number of NCFs in the cluster with a state up";
    }
  }

  notification NCP_NPU_SOFT_RESTART {
    description
      "The NCP Network Processing Unit (NPU) failed and recovered by performing a soft restart.";
    dn-events-extensions:event-severity-level "Error";
    dn-events-extensions:event-message-string "NCP {ncp-id} Network Processing Unit encountered a problem and recovered by performing a soft restart type {restart-type}";
    dn-events-extensions:event-corrective-action-string "Contact Customer Support.";
    dn-events-extensions:event-trigger-component-string "WB Agent";
    dn-events-extensions:event-group "System";
    leaf ncp-id {
      type uint16;
      description
        "NCP ID";
    }
    leaf restart-type {
      type string;
      description
        "Type of soft restart performed by the NPU";
    }
  }

  notification NCP_NPU_HARD_RESTART {
    description
      "The NCP Network Processing Unit (NPU) failed, the NCP is being restarted.";
    dn-events-extensions:event-severity-level "Error";
    dn-events-extensions:event-message-string "NCP {ncp-id} Network Processing Unit encountered a problem, NCP will restart";
    dn-events-extensions:event-corrective-action-string "Contact Customer Support.";
    dn-events-extensions:event-trigger-component-string "WB Agent";
    dn-events-extensions:event-group "System";
    leaf ncp-id {
      type uint16;
      description
        "NCP ID";
    }
  }

  notification NCM_NPU_HARD_RESTART {
    description
      "The NCM Network Processing Unit (NPU) failed, the NCM is being restarted.";
    dn-events-extensions:event-severity-level "Error";
    dn-events-extensions:event-message-string "NCM {ncm-id} Network Processing Unit encountered a problem, NCM will restart";
    dn-events-extensions:event-corrective-action-string "Contact Customer Support.";
    dn-events-extensions:event-trigger-component-string "WB Agent";
    dn-events-extensions:event-group "System";
    leaf ncm-id {
      type uint16;
      description
        "NCM ID";
    }
  }

  notification NCF_NPU_SOFT_RESTART {
    description
      "The NCF Network Processing Unit (NPU) failed and recovered by performing a soft restart.";
    dn-events-extensions:event-severity-level "Error";
    dn-events-extensions:event-message-string "NCF {ncf-id} Network Processing Unit encountered a problem and recovered by performing a soft restart type {restart-type}";
    dn-events-extensions:event-corrective-action-string "Contact Customer Support.";
    dn-events-extensions:event-trigger-component-string "WB Agent";
    dn-events-extensions:event-group "System";
    leaf ncf-id {
      type uint16;
      description
        "NCF ID";
    }
    leaf restart-type {
      type string;
      description
        "Type of soft restart performed by the NPU";
    }
  }

  notification NCM_NPU_SOFT_RESTART {
    description
      "The NCM Network Processing Unit (NPU) failed and recovered by performing a soft restart.";
    dn-events-extensions:event-severity-level "Error";
    dn-events-extensions:event-message-string "NCM {ncm-id} Network Processing Unit encountered a problem and recovered by performing a soft restart type {restart-type}";
    dn-events-extensions:event-corrective-action-string "Contact Customer Support.";
    dn-events-extensions:event-trigger-component-string "WB Agent";
    dn-events-extensions:event-group "System";
    leaf ncm-id {
      type uint16;
      description
        "NCM ID";
    }
    leaf restart-type {
      type string;
      description
        "Type of soft restart performed by the NPU";
    }
  }

  notification NCF_NPU_HARD_RESTART {
    description
      "The NCF Network Processing Unit (NPU) failed, the NCF is being restarted.";
    dn-events-extensions:event-severity-level "Error";
    dn-events-extensions:event-message-string "NCF {ncf-id} Network Processing Unit encountered a problem, NCF will restart";
    dn-events-extensions:event-corrective-action-string "Contact Customer Support.";
    dn-events-extensions:event-trigger-component-string "WB Agent";
    dn-events-extensions:event-group "System";
    leaf ncf-id {
      type uint16;
      description
        "NCF ID";
    }
  }

  notification SYSTEM_NCE_HIGH_TASKS_NO_LEVEL_REACHED {
    description
      "NCE reached high level of tasks number running";
    dn-events-extensions:event-severity-level "Warning";
    dn-events-extensions:event-message-string "NCE {nce}-{nce-id} reached high level of task number {tasks-number}.";
    dn-events-extensions:event-corrective-action-string "No corrective action.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf tasks-number {
      type uint16;
      description
        "Number of tasks running on the NCE";
    }
  }

  notification SYSTEM_NCE_HIGH_TASKS_NO_LEVEL_CLEARED {
    description
      "The number of tasks running on the NCE went below the high level";
    dn-events-extensions:event-severity-level "Info";
    dn-events-extensions:event-message-string "Number of tasks running on NCE {nce}-{nce-id} is {tasks-number} and is below the high level";
    dn-events-extensions:event-corrective-action-string "No corrective action.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf tasks-number {
      type uint16;
      description
        "Number of tasks running on the NCE";
    }
  }

  // FIB events

  notification FIB_INSTALL_ERROR {
    description
      "An NCP failed to install a FIB element";
    dn-events-extensions:event-severity-level "Critical";
    dn-events-extensions:event-message-string "NCP {ncp-id} failed to install {fib-object}, due to {error-reason}";
    dn-events-extensions:event-corrective-action-string "Verify routing hasn't exceeded the supported system scale";
    dn-events-extensions:event-trigger-component-string "WB Agent";
    dn-events-extensions:event-group "fib-manager";
    leaf ncp-id {
      type uint16;
      description
        "NCP ID";
    }
    leaf fib-object {
      type string;
      description
        "type of fib fib object - route , label or nexthop. followed by object detail
         route - the prefix
         label - label value
         nexthop - nexthop address, egress interface and label";
    }
    leaf error-reason {
      type string;
      description
        "error reason for installation failure - can be HW received error, missing id, etc...";
    }
  }

  notification FIB_EGRESS_OBJECT_LIMIT_REACHED {
    description
      "The number of FIB egress objects has reached the maximum number of system supported scale.";
    dn-events-extensions:event-severity-level "Warning";
    dn-events-extensions:event-message-string "Number of FIB egress objects has reached the system maximum scale limit of {limit}";
    dn-events-extensions:event-corrective-action-string "No corrective action.";
    dn-events-extensions:event-trigger-component-string "fib-manager";
    dn-events-extensions:event-group "fib-manager";
    leaf limit {
      type uint8;
      description
        "System FIB egress objects max limit";
    }
  }

  notification FIB_EGRESS_OBJECT_LIMIT_CLEARED {
    description
      "The number of FIB egress objects is below the system limit.";
    dn-events-extensions:event-severity-level "Info";
    dn-events-extensions:event-message-string "Number of FIB egress objects is below the system limit of {limit}";
    dn-events-extensions:event-corrective-action-string "This is informational, no corrective action required.";
    dn-events-extensions:event-trigger-component-string "fib-manager";
    dn-events-extensions:event-group "fib-manager";
    leaf limit {
      type uint16;
      description
        "System FIB egress objects max limit";
    }
  }

  notification FIB_EGRESS_OBJECT_THRESHOLD_EXCEEDED {
    description
      "The number of FIB egress objects crossed the maximum supported threshold.";
    dn-events-extensions:event-severity-level "Warning";
    dn-events-extensions:event-message-string "Number of FIB egress objects has crossed the system threshold {threshold}% of the limit ({limit}), the number of FIB egress objects is ({numeric-value})";
    dn-events-extensions:event-corrective-action-string "No corrective action.";
    dn-events-extensions:event-trigger-component-string "fib-manager";
    dn-events-extensions:event-group "fib-manager";
    leaf threshold {
      type uint8;
      description
        "Threshold percent";
    }
    leaf numeric-value {
      type uint16;
      description
        "Current number of FIB egress objects";
    }
    leaf limit {
      type uint16;
      description
        "System FIB egress objects max limit";
    }
  }

  notification FIB_EGRESS_OBJECT_THRESHOLD_CLEARED {
    description
      "The number of FIB egress objects is below the threshold.";
    dn-events-extensions:event-severity-level "Info";
    dn-events-extensions:event-message-string "Number of FIB egress objects is below the threshold {threshold}% of the limit ({limit}), the number of FIB egress objects is ({numeric-value})";
    dn-events-extensions:event-corrective-action-string "This is informational, no corrective action required.";
    dn-events-extensions:event-trigger-component-string "fib-manager";
    dn-events-extensions:event-group "fib-manager";
    leaf threshold {
      type uint8;
      description
        "Threshold percent";
    }
    leaf numeric-value {
      type uint16;
      description
        "Current number of FIB egress objects";
    }
    leaf limit {
      type uint16;
      description
        "System FIB egress objects max limit";
    }
  }

  notification FIB_WECMP_PROFILE_THRESHOLD_REACHED {
    description
      "The number of FIB weighted ecmp hardware profiles crossed the maximum supported threshold.";
    dn-events-extensions:event-severity-level "Warning";
    dn-events-extensions:event-message-string "NCP {ncp-id}: Number of FIB Weighted ECMP profiles has crossed the system threshold of {threshold}% of overall system support. Using {small} small Weighted ECMP profiles and {medium} medium Weighted ECMP proiles";
    dn-events-extensions:event-corrective-action-string "Reduce ECMP maximum-path";
    dn-events-extensions:event-trigger-component-string "fib-manager";
    dn-events-extensions:event-group "fib-manager";
    leaf ncp-id {
      type uint16;
      description
        "NCP ID";
    }
    leaf threshold {
      type uint8;
      description
        "Threshold percent";
    }
    leaf small {
      type uint16;
      description
        "Current number of small profile tables";
    }
    leaf medium {
      type uint16;
      description
        "Current number of medium profile tables";
    }
  }

  notification FIB_WECMP_PROFILE_THRESHOLD_CLEARED {
    description
      "The number of FIB weighted ecmp hardware profiles is below the maximum supported threshold.";
    dn-events-extensions:event-severity-level "Info";
    dn-events-extensions:event-message-string "NCP {ncp-id}: Number of FIB Weighted ECMP profiles is below {threshold}% of overall system support. Using {small} small Weighted ECMP profiles and {medium}  Weighted ECMP proiles";
    dn-events-extensions:event-corrective-action-string "This is informational, no corrective action required.";
    dn-events-extensions:event-trigger-component-string "fib-manager";
    dn-events-extensions:event-group "fib-manager";
    leaf ncp-id {
      type uint16;
      description
        "NCP ID";
    }
    leaf threshold {
      type uint8;
      description
        "Threshold percent";
    }
    leaf small {
      type uint16;
      description
        "Current number of small profile tables";
    }
    leaf medium {
      type uint16;
      description
        "Current number of medium profile tables";
    }
  }

  notification FIB_FAILED_TO_ALLOCATE_WECMP_PROFILE {
    description
      "FIB failed to provide weighted ecmp routing entry and will fallback to uniform ecmp";
    dn-events-extensions:event-severity-level "Notice";
    dn-events-extensions:event-message-string "NCP {ncp-id}: FIB failed to allocate Weighted ECMP profile due to {failure-reason}. Uniform ECMP will be provided. Required weighted ECMP structure {weight-group} for nexthop-oid {nhoid}";
    dn-events-extensions:event-corrective-action-string "Reduce ECMP maximum-path";
    dn-events-extensions:event-trigger-component-string "fib-manager";
    dn-events-extensions:event-group "fib-manager";
    leaf ncp-id {
      type uint16;
      description
        "NCP ID";
    }
    leaf failure-reason {
      type string;
      description
        "string of failure reason. For example, 'out of resource'";
    }
    leaf weight-group {
      type string;
      description
        "list specifing the required profile. number of members and weight of each member";
    }
    leaf nhoid {
      type string;
      description
        "the nhoid that required the weighted ecmp group";
    }
  }

  notification NCP_FIB_DISCONNECTED_FROM_RIB {
    description
      "The FIB installation disconnected from the RIB on the listed NCP.";
    dn-events-extensions:event-severity-level "Notice";
    dn-events-extensions:event-message-string "NCP {ncp-id} FIB disconnected from RIB. Routing updates will not be installed for the NCP";
    dn-events-extensions:event-corrective-action-string "Verify the NCP backplane control connectivity and check the control drop counters.";
    dn-events-extensions:event-trigger-component-string "fib-manager";
    dn-events-extensions:event-group "fib-manager";
    leaf ncp-id {
      type uint16;
      description
        "NCP ID";
    }
  }

  notification NCP_FIB_CONNECTED_TO_RIB {
    description
      "The listed  NCP connected to the  RIB for FIB installations.";
    dn-events-extensions:event-severity-level "Info";
    dn-events-extensions:event-message-string "NCP {ncp-id} FIB connected to RIB. Routing updates will be installed for the NCP";
    dn-events-extensions:event-corrective-action-string "This is informational, no corrective action required.";
    dn-events-extensions:event-trigger-component-string "fib-manager";
    dn-events-extensions:event-group "fib-manager";
    leaf ncp-id {
      type uint16;
      description
        "NCP ID";
    }
  }

  // HA events

  notification NCC_FAILOVER {
    description
      "The system triggered the NCC switchover. The reason for switchover can vary from an NCC node failure to a failure of a non-restartable process.";
    dn-events-extensions:event-severity-level "Error";
    dn-events-extensions:event-message-string "Active NCC failover from {ncc-id-failed} to {ncc-id-stb}";
    dn-events-extensions:event-corrective-action-string "This is informational, no corrective action required.";
    dn-events-extensions:event-trigger-component-string "HA-manager";
    dn-events-extensions:event-group "System";
    dn-events-extensions:event-snmp-trap-name "dnNccFailover";
    dn-events-extensions:event-snmp-trap-oid ".1.3.6.1.4.1.49739.2.9.0.1";
    dn-events-extensions:event-snmp-trap-vars "dnNccIdFailed.0 {ncc-id-failed} ; dnNccIdStb.0 {ncc-id-stb}";
    leaf ncc-id-failed {
      type uint8;
      description
        "Active NCC ID that has failed";
    }
    leaf ncc-id-stb {
      type uint8;
      description
        "Standby NCC ID that takes over from the failed NCC";
    }
  }

  notification NCC_SWITCHOVER_USER {
    description
      "The user has requested an NCC switchover";
    dn-events-extensions:event-severity-level "Info";
    dn-events-extensions:event-message-string "User {user-name} has requested NCC switchover from NCC {ncc-id-active} to NCC {ncc-id-old-standby}";
    dn-events-extensions:event-corrective-action-string "This is informational, no corrective action required.";
    dn-events-extensions:event-trigger-component-string "HA-manager";
    dn-events-extensions:event-group "System";
    dn-events-extensions:event-snmp-trap-name "dnNccSwitchoverUser";
    dn-events-extensions:event-snmp-trap-oid ".1.3.6.1.4.1.49739.2.9.0.2";
    dn-events-extensions:event-snmp-trap-vars "dnUserName.0 {user-name} ; dnNccIdAct.0 {ncc-id-active} ; dnNccOldStb.0 {ncc-id-old-standby}";
    leaf user-name {
      type string;
      description
        "System user-name";
    }
    leaf ncc-id-active {
      type uint8;
      description
        "Active NCC ID on which user requested switchover";
    }
    leaf ncc-id-old-standby {
      type uint8;
      description
        "Standby NCC ID for which user requested switchover to";
    }
  }

  notification NCC_PRIMARY_CONFIG_CHANGE {
    description
      "The user has configured the indicated NCC to be the preferred primary NCC.";
    dn-events-extensions:event-severity-level "Info";
    dn-events-extensions:event-message-string "User {user-name} has configured NCC {ncc-id} to be the preferred primary NCC for the DNOS cluster";
    dn-events-extensions:event-corrective-action-string "This is informational, no corrective action required.";
    dn-events-extensions:event-trigger-component-string "HA-manager";
    dn-events-extensions:event-group "System";
    leaf user-name {
      type string;
      description
        "System user-name";
    }
    leaf ncc-id {
      type uint8;
      description
        "NCC ID";
    }
  }

  notification SYSTEM_COLD_START {
    description
      "The system has started (cold start).";
    dn-events-extensions:event-severity-level "Info";
    dn-events-extensions:event-message-string "System has started (cold start)";
    dn-events-extensions:event-corrective-action-string "This is informational, no corrective action required.";
    dn-events-extensions:event-trigger-component-string "HA-manager";
    dn-events-extensions:event-group "System";
    dn-events-extensions:event-snmp-trap-name "coldStart";
    dn-events-extensions:event-snmp-trap-generic-type "coldStart";
    dn-events-extensions:event-snmp-trap-oid "1.3.6.1.6.3.1.1.5.1";
    dn-events-extensions:event-snmp-trap-reachability "True";
  }

  notification SYSTEM_WARM_START {
    description
      "The system has started (warm start).";
    dn-events-extensions:event-severity-level "Info";
    dn-events-extensions:event-message-string "System has started (warm start)";
    dn-events-extensions:event-corrective-action-string "This is informational, no corrective action required.";
    dn-events-extensions:event-trigger-component-string "HA-manager";
    dn-events-extensions:event-group "System";
    dn-events-extensions:event-snmp-trap-name "warmStart";
    dn-events-extensions:event-snmp-trap-generic-type "warmStart";
    dn-events-extensions:event-snmp-trap-oid "1.3.6.1.6.3.1.1.5.2";
    dn-events-extensions:event-snmp-trap-reachability "True";
  }

  notification SYSTEM_PROCESS_HELD_DOWN {
    description
      "The system process is held down by high-availability policy due to multiple HA violations.";
    dn-events-extensions:event-severity-level "Warning";
    dn-events-extensions:event-message-string "Process {nce}-{nce-id}:{container-name} : {process-name} is held down by high-availability policy.";
    dn-events-extensions:event-corrective-action-string "Manually restart process to bring it back up";
    dn-events-extensions:event-trigger-component-string "HA-manager";
    dn-events-extensions:event-group "System";
    leaf nce {
      description
        "name of element which process resign, ncc, ncf, ncp";
      type string;
    }
    leaf nce-id {
      description
        "id of the nce element";
      type string;
    }
    leaf process-name {
      type string;
      description
        "System process name (e.g. bgpd, ospfd, CLI)";
    }
    leaf container-name {
      type string;
      description
        "System container name (e.g. routing-engine)";
    }
  }

  notification SYSTEM_PROCESS_STOP {
    description
      "The listed user stopped the system process.";
    dn-events-extensions:event-severity-level "Notice";
    dn-events-extensions:event-message-string "User {user-name} stopped process {nce}-{nce-id} : {container-name} : {process-name}.";
    dn-events-extensions:event-corrective-action-string "Restart the process to start the process.";
    dn-events-extensions:event-trigger-component-string "HA-manager";
    dn-events-extensions:event-group "System";
    leaf user-name {
      type string;
      description
        "System user-name";
    }
    leaf nce {
      description
        "name of element which process resign, ncc, ncf, ncp";
      type string;
    }
    leaf nce-id {
      description
        "id of the nce element";
      type string;
    }
    leaf process-name {
      type string;
      description
        "System process name (e.g. bgpd, ospfd, CLI)";
    }
    leaf container-name {
      type string;
      description
        "System container name (e.g. routing-engine)";
    }
  }

  notification SYSTEM_PROCESS_RESTART {
    description
      "The system has restarted the process indicated due to a process failure.";
    dn-events-extensions:event-severity-level "Error";
    dn-events-extensions:event-message-string "System restarted the process {nce}-{nce-id}:{container-name} : {process-name}. {error-message}";
    dn-events-extensions:event-corrective-action-string "No corrective action.";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf error-message {
      type string;
      description
        "Error description or reason";
    }
  }

  notification SYSTEM_PROCESS_HA_VIOLATION {
    description
      "The system process has violated the high-availability policy.";
    dn-events-extensions:event-severity-level "Error";
    dn-events-extensions:event-message-string "System process {nce}-{nce-id}:{container-name} : {process-name} "
                                            + "has violated the high-availability policy. Process exited {num-mitigation} times in {period} seconds. "
                                            + "High-availability escalation action: {escalation-action}";
    dn-events-extensions:event-corrective-action-string "No corrective action.";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf num-mitigation {
      description
        "Number of mitigations in period allowed for process per HA policy";
      type string;
    }
    leaf period {
      description
        "Mitigation period duration specified in HA policy. in seconds";
      type string;
    }
    leaf escalation-action {
      description
        "HA action upon the violation, either list of entities restarted";
      type string;
    }
  }

  notification SYSTEM_PROCESS_FAILED {
    description
      "The system has detected that a process failed and is no longer running.";
    dn-events-extensions:event-severity-level "Error";
    dn-events-extensions:event-message-string "System process {nce}-{nce-id}:{container-name} : {process-name} failed. Process importance: {importance}";
    dn-events-extensions:event-corrective-action-string "Review process logs for failure reason";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf importance {
      description
        "entity HA importance in system, regular, essential or critical";
      type string;
    }
  }

  notification PROCESS_OPERATIONAL_DATA_RESYNC {
    description
      "Process is resynchronizing its operational database. Counters may be reset or suffer discontinuities.";
    dn-events-extensions:event-severity-level "Error";
    dn-events-extensions:event-message-string "Process {process-name} is resynchronizing its operational data due to failure to update the datastore. Counters maintained by the process may be reset or suffer discontinuities.";
    dn-events-extensions:event-corrective-action-string "No corrective action required.";
    dn-events-extensions:event-trigger-component-string "Operational-infra";
    dn-events-extensions:event-group "System";
    leaf process-name {
      type string;
      description
        "System process name (e.g. bgpd, ospfd, CLI).";
    }
  }

  notification PROCESS_ABNORMAL_MEMORY_USAGE {
    description
      "System detected abnormal process memory consumption";
    dn-events-extensions:event-severity-level "Warning";
    dn-events-extensions:event-message-string "System process {nce}-{nce-id}:{container-name} : {process-name} detected with abnormal memory consumption. Process RSS memory {memory-in-use} KB. Process PID {process-id} exec-cmd {exec-cmd}";
    dn-events-extensions:event-corrective-action-string "Investigate process memory usage. Reduce system scale or restart/stop process. In the case of memory leaks, contact Customer Support.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf memory-in-use {
      description
        "The amount of RAM used by the process in human readable format";
      type string;
    }
    leaf process-id {
      description
        "process id on baseOS";
      type string;
    }
    leaf exec-cmd {
      description
        "baseOS process execution command";
      type string;
    }
  }

  notification PROCESS_ABNORMAL_MEMORY_USAGE_CLEARED {
    description
      "System process memory consumption stablizied and went below 95% of expected memory upper limit";
    dn-events-extensions:event-severity-level "Info";
    dn-events-extensions:event-message-string "System process {nce}-{nce-id}:{container-name} : {process-name} memory consumption stablizied and went below 95% of expected memory upper limit. Process RSS memory {memory-in-use} KB. Process PID {process-id} exec-cmd {exec-cmd}";
    dn-events-extensions:event-corrective-action-string "This is informational, no corrective action required.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf memory-in-use {
      description
        "The amount of RAM used by the process in human readable format";
      type string;
    }
    leaf process-id {
      description
        "process id on baseOS";
      type string;
    }
    leaf exec-cmd {
      description
        "baseOS process execution command";
      type string;
    }
  }

  notification SYSTEM_CONTAINER_RESTART {
    description
      "The container described in the text was restarted by the system.";
    dn-events-extensions:event-severity-level "Error";
    dn-events-extensions:event-message-string "System restarted container {nce}-{nce-id}:{container-name}";
    dn-events-extensions:event-corrective-action-string "This is informational, no corrective action required.";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf container-name {
      type string;
      description
        "System container name (e.g. routing-engine)";
    }
  }

  notification SYSTEM_CONTAINER_HA_VIOLATION {
    description
      "The system container has violated the high-availability policy.";
    dn-events-extensions:event-severity-level "Error";
    dn-events-extensions:event-message-string "System container {nce}-{nce-id}:{container-name} "
                                            + "has violated the high-availability policy. Container exited {num-mitigation} times in {period} seconds. "
                                            + "High-availability escalation action: {escalation-action}";
    dn-events-extensions:event-corrective-action-string "No corrective action.";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf container-name {
      type string;
      description
        "System container name (e.g. routing-engine)";
    }
    leaf num-mitigation {
      description
        "Number of mitigations in period allowed for process per HA policy";
      type string;
    }
    leaf period {
      description
        "Mitigation period duration specified in HA policy. in seconds";
      type string;
    }
    leaf escalation-action {
      description
        "HA action upon the violation, restart node";
      type string;
    }
  }

  notification SYSTEM_CONTAINER_FAILED {
    description
      "The system has detected that a container failed and is no longer running.";
    dn-events-extensions:event-severity-level "Error";
    dn-events-extensions:event-message-string "System container {nce}-{nce-id}:{container-name} failed. Container importance: {importance}";
    dn-events-extensions:event-corrective-action-string "This is informational, no corrective action required";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf container-name {
      type string;
      description
        "System container name (e.g. routing-engine)";
    }
    leaf importance {
      description
        "entity HA importance in system, regular, essential or critical";
      type string;
    }
  }

  notification SYSTEM_COLD_RESTART_USER {
    description
      "The system was restarted intentionally by the user listed using the CLI command 'request system restart'.";
    dn-events-extensions:event-severity-level "Warning";
    dn-events-extensions:event-message-string "User {user-name} has requested a cold system restart";
    dn-events-extensions:event-corrective-action-string "No corrective action.";
    dn-events-extensions:event-trigger-component-string "Transaction-manager";
    dn-events-extensions:event-group "System";
    leaf user-name {
      type string;
      description
        "System user-name";
    }
  }

  notification SYSTEM_WARM_RESTART_USER {
    description
      "The system was restarted intentionally by the user listed using the CLI command 'request system restart warm'.";
    dn-events-extensions:event-severity-level "Warning";
    dn-events-extensions:event-message-string "User {user-name} has requested a warm system restart";
    dn-events-extensions:event-corrective-action-string "No corrective action.";
    dn-events-extensions:event-trigger-component-string "Transaction-manager";
    dn-events-extensions:event-group "System";
    leaf user-name {
      type string;
      description
        "System user-name";
    }
  }

  notification SYSTEM_PROCESS_RESTART_USER {
    description
      "The user has restarted the indicated process.";
    dn-events-extensions:event-severity-level "Info";
    dn-events-extensions:event-message-string "User {user-name} has restarted process {nce}-{nce-id}: {container-name} : {process-name}";
    dn-events-extensions:event-corrective-action-string "This is informational, no corrective action required.";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf container-name {
      type string;
      description
        "System container name (e.g. routing-engine)";
    }
    leaf process-name {
      type string;
      description
        "System process name (e.g. bgpd, ospfd, CLI)";
    }
    leaf user-name {
      type string;
      description
        "System user-name";
    }
  }

  notification SYSTEM_CONTAINER_RESTART_USER {
    description
      "The user has restarted the indicated container.";
    dn-events-extensions:event-severity-level "Info";
    dn-events-extensions:event-message-string "User {user-name} has restarted container {nce}-{nce-id}:{container-name}";
    dn-events-extensions:event-corrective-action-string "This is informational, no corrective action required.";
    dn-events-extensions:event-trigger-component-string "HA-manager";
    dn-events-extensions:event-group "System";
    leaf nce {
      description
        "Name of element where the process resides, NCC, NCF, NCP";
      type string;
    }
    leaf nce-id {
      description
        "ID of the NCE element";
      type string;
    }
    leaf container-name {
      type string;
      description
        "System container name (e.g. routing-engine)";
    }
    leaf user-name {
      type string;
      description
        "System user-name";
    }
  }

  // Process monitoring events

  notification PROCESS_MEMORY_WARNING_LEVEL_REACHED {
    description
      "Process reached warning level of memory consumption";
    dn-events-extensions:event-severity-level "Warning";
    dn-events-extensions:event-message-string "Process {nce}-{nce-id}:{container-name} : {process-name} reached warning level of memory consumption. Process memory consumption is {memory-in-use}. Process PID {process-id} exec-cmd {exec-cmd}";
    dn-events-extensions:event-corrective-action-string "No corrective action.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf memory-in-use {
      description
        "The amount of RAM used by the process in human readable format";
      type string;
    }
    leaf process-id {
      description
        "process id on host";
      type string;
    }
    leaf exec-cmd {
      description
        "process execution command";
      type string;
    }
  }

  notification PROCESS_MEMORY_WARNING_LEVEL_CLEARED {
    description
      "Process memory consumption went below the warning level";
    dn-events-extensions:event-severity-level "Info";
    dn-events-extensions:event-message-string "System process {nce}-{nce-id}:{container_name} : {process-name} memory consumption went below the warning level. Process memory {memory-in-use}. Process PID {process-id} exec-cmd {exec-cmd}";
    dn-events-extensions:event-corrective-action-string "No corrective action.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf memory-in-use {
      description
        "The amount of RAM used by the process in human readable format";
      type string;
    }
    leaf process-id {
      description
        "process id on host";
      type string;
    }
    leaf exec-cmd {
      description
        "process execution command";
      type string;
    }
  }

  notification PROCESS_MEMORY_CRITICAL_LEVEL_REACHED {
    description
      "Process reached critical level of memory consumption";
    dn-events-extensions:event-severity-level "Critical";
    dn-events-extensions:event-message-string "Process {nce}-{nce-id}:{container_name} : {process-name} reached critical level of memory consumption. Process memory consumption is {memory-in-use}. Process PID {process-id} exec-cmd {exec-cmd}";
    dn-events-extensions:event-corrective-action-string "Investigate process memory usage. Reduce system scale or restart/stop process.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf memory-in-use {
      description
        "The amount of RAM used by the process in human readable format";
      type string;
    }
    leaf process-id {
      description
        "process id on host";
      type string;
    }
    leaf exec-cmd {
      description
        "process execution command";
      type string;
    }
  }

  notification PROCESS_MEMORY_CRITICAL_LEVEL_CLEARED {
    description
      "Process memory consumption went below the critical level";
    dn-events-extensions:event-severity-level "Info";
    dn-events-extensions:event-message-string "System process {nce}-{nce-id}:{container_name} : {process-name} memory consumption went below the critical level. Process memory {memory-in-use}. Process PID {process-id} exec-cmd {exec-cmd}";
    dn-events-extensions:event-corrective-action-string "This is informational, no corrective action required.";
    dn-events-extensions:event-trigger-component-string "Operational-infra";
    dn-events-extensions:event-group "Monitoring";
    leaf nce {
      description
        "Name of element where the process resides, NCC, NCF, NCP";
      type string;
    }
    leaf nce-id {
      description
        "ID of the NCE element";
      type string;
    }
    leaf process-name {
      type string;
      description
        "System process name (e.g. bgpd, ospfd, CLI)";
    }
    leaf container-name {
      type string;
      description
        "System container name (e.g. routing-engine)";
    }
    leaf memory-in-use {
      description
        "The amount of RAM used by the process in human readable format";
      type string;
    }
    leaf process-id {
      description
        "process id on host";
      type string;
    }
    leaf exec-cmd {
      description
        "process execution command";
      type string;
    }
  }

  notification PROCESS_CPU_WARNING_LEVEL_REACHED {
    description
      "Process cpu reached warning level of consumption";
    dn-events-extensions:event-severity-level "Warning";
    dn-events-extensions:event-message-string "Process {container-name}:{process-name} on {node-type} {node-id} reached {cpu-in-use}% CPU consumption. PID {process-id} exec-cmd {exec-cmd}";
    dn-events-extensions:event-corrective-action-string "This is informational, no corrective action required.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf cpu-in-use {
      description
        "The percentage of CPU used by the process";
      type string;
    }
    leaf process-id {
      description
        "process id on host";
      type string;
    }
    leaf exec-cmd {
      description
        "process execution command";
      type string;
    }
  }

  notification PROCESS_CPU_WARNING_LEVEL_CLEARED {
    description
      "Process cpu consumption went below the warning level";
    dn-events-extensions:event-severity-level "Info";
    dn-events-extensions:event-message-string "Process {container-name}:{process-name} on {node-type} {node-id} CPU consumption warning cleared. PID {process-id} exec-cmd {exec-cmd}";
    dn-events-extensions:event-corrective-action-string "No corrective action.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf cpu-in-use {
      description
        "The percentage of CPU used by the process";
      type string;
    }
    leaf process-id {
      description
        "process id on host";
      type string;
    }
    leaf exec-cmd {
      description
        "process execution command";
      type string;
    }
  }

  notification PROCESS_CPU_CRITICAL_LEVEL_REACHED {
    description
      "Process cpu reached critical level of consumption";
    dn-events-extensions:event-severity-level "Critical";
    dn-events-extensions:event-message-string "Process {container-name}:{process-name} on {node-type} {node-id} reached {cpu-in-use}% CPU consumption. PID {process-id} exec-cmd {exec-cmd}";
    dn-events-extensions:event-corrective-action-string "No corrective action required.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf cpu-in-use {
      description
        "The percentage of CPU used by the process";
      type string;
    }
    leaf process-id {
      description
        "process id on host";
      type string;
    }
    leaf exec-cmd {
      description
        "process execution command";
      type string;
    }
  }

  notification PROCESS_CPU_CRITICAL_LEVEL_CLEARED {
    description
      "Process cpu consumption went below the critical level";
    dn-events-extensions:event-severity-level "Info";
    dn-events-extensions:event-message-string "Process {container-name}:{process-name} on {node-type} {node-id} CPU consumption critical cleared. PID {process-id} exec-cmd {exec-cmd}";
    dn-events-extensions:event-corrective-action-string "This is informational, no corrective action required.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf cpu-in-use {
      description
        "The percentage of CPU used by the process";
      type string;
    }
    leaf process-id {
      description
        "process id on host";
      type string;
    }
    leaf exec-cmd {
      description
        "process execution command";
      type string;
    }
  }

  notification PROCESS_FILE_DESCRIPTORS_WARNING_LEVEL_REACHED {
    description
      "Process file descriptors reached warning level of usage";
    dn-events-extensions:event-severity-level "Warning";
    dn-events-extensions:event-message-string "Process {container-name}:{process-name} on {node-type} {node-id} reached {fd-in-use} file descriptors. PID {process-id} exec-cmd {exec-cmd}";
    dn-events-extensions:event-corrective-action-string "This is informational, no corrective action required.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf fd-in-use {
      description
        "Total file descriptors used by the process";
      type string;
    }
    leaf process-id {
      description
        "process id on host";
      type string;
    }
    leaf exec-cmd {
      description
        "process execution command";
      type string;
    }
  }

  notification PROCESS_FILE_DESCRIPTORS_WARNING_LEVEL_CLEARED {
    description
      "Process file descriptors went below the warning level";
    dn-events-extensions:event-severity-level "Info";
    dn-events-extensions:event-message-string "Process {container-name}:{process-name} on {node-type} {node-id} FD warning consumption cleared. PID {process-id} exec-cmd {exec-cmd}";
    dn-events-extensions:event-corrective-action-string "This is informational, no corrective action required.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf fd-in-use {
      description
        "Total file descriptors used by the process";
      type string;
    }
    leaf process-id {
      description
        "process id on host";
      type string;
    }
    leaf exec-cmd {
      description
        "process execution command";
      type string;
    }
  }

  notification PROCESS_FILE_DESCRIPTORS_CRITICAL_LEVEL_REACHED {
    description
      "Process file descriptors reached critical level of usage";
    dn-events-extensions:event-severity-level "Critical";
    dn-events-extensions:event-message-string "Process {container-name}:{process-name} on {node-type} {node-id} reached {fd-in-use} file descriptors. PID {process-id} exec-cmd {exec-cmd}";
    dn-events-extensions:event-corrective-action-string "No corrective action required.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf fd-in-use {
      description
        "Total file descriptors used by the process";
      type string;
    }
    leaf process-id {
      description
        "process id on host";
      type string;
    }
    leaf exec-cmd {
      description
        "process execution command";
      type string;
    }
  }

  notification PROCESS_FILE_DESCRIPTORS_CRITICAL_LEVEL_CLEARED {
    description
      "Process file descriptors went below the critical level";
    dn-events-extensions:event-severity-level "Info";
    dn-events-extensions:event-message-string "Process {container-name}:{process-name} on {node-type} {node-id} FD critical consumption cleared. PID {process-id} exec-cmd {exec-cmd}";
    dn-events-extensions:event-corrective-action-string "This is informational, no corrective action required.";
    dn-events-extensions:event-trigger-component-string "Operational-infra";
    dn-events-extensions:event-group "Monitoring";
    leaf node-type {
      description
        "Name of element where the process resides, NCC, NCF, NCP";
      type string;
    }
    leaf node-id {
      description
        "ID of the NCE element";
      type string;
    }
    leaf process-name {
      type string;
      description
        "System process name (e.g. bgpd, ospfd, CLI)";
    }
    leaf container-name {
      type string;
      description
        "System container name (e.g. routing-engine)";
    }
    leaf fd-in-use {
      description
        "Total file descriptors used by the process";
      type string;
    }
    leaf process-id {
      description
        "process id on host";
      type string;
    }
    leaf exec-cmd {
      description
        "process execution command";
      type string;
    }
  }

  // SZTP events

  notification SZTP_NO_SERVERS_FOUND {
    description
      "Secure Zero Touch Provisioning did not find any configured servers.";
    dn-events-extensions:event-severity-level "Info";
    dn-events-extensions:event-message-string "No SZTP servers could be found for provisioning.";
    dn-events-extensions:event-corrective-action-string "Verify SZTP server configuration";
    dn-events-extensions:event-trigger-component-string "SZTP Client";
    dn-events-extensions:event-group "Management";
  }

  notification SZTP_ATTEMPT_REQUEST_FAILED {
    description
      "A request to the SZTP bootstrap server has failed, indicating an error in obtaining onboarding information";
    dn-events-extensions:event-severity-level "Notice";
    dn-events-extensions:event-message-string "Unable to obtain onboarding information from the SZTP bootstrap server at {server-address}:{port}. error: {error-message}";
    dn-events-extensions:event-corrective-action-string "Check the bootstrap server status, verify network connectivity, and examine the provided error message for specific troubleshooting steps";
    dn-events-extensions:event-trigger-component-string "SZTP Client";
    dn-events-extensions:event-group "Management";
    leaf server-address {
      type string;
      description
        "Address of the SZTP bootstrap server";
    }
    leaf port {
      type uint16;
      description
        "Port of the SZTP bootstrap server";
    }
    leaf error-message {
      type string;
      description
        "The error message that describes what is the failure reason";
    }
  }

  notification SZTP_ATTEMPT_REQUEST_SUCCEEDED {
    description
      "A request to the SZTP bootstrap server was successful";
    dn-events-extensions:event-severity-level "Info";
    dn-events-extensions:event-message-string "Successfully processed request with SZTP bootstrap server at {server-address}:{port}";
    dn-events-extensions:event-corrective-action-string "This is informational, no corrective action required";
    dn-events-extensions:event-trigger-component-string "SZTP Client";
    dn-events-extensions:event-group "Management";
    leaf server-address {
      type string;
      description
        "Address of the SZTP bootstrap server";
    }
    leaf port {
      type uint16;
      description
        "Port of the SZTP bootstrap server";
    }
  }

  notification SZTP_FLOW_START {
    description
      "The SZTP provisioning flow has started. After this notification, the system will attempt to retrieve onboarding information from the list of SZTP bootstrap server.";
    dn-events-extensions:event-severity-level "Info";
    dn-events-extensions:event-message-string "System starting SZTP flow";
    dn-events-extensions:event-corrective-action-string "No corrective action required";
    dn-events-extensions:event-trigger-component-string "SZTP Client";
    dn-events-extensions:event-group "Management";
  }

  notification SZTP_ATTEMPT_STATE_CHANGE {
    description
      "The SZTP attempt state has changed.";
    dn-events-extensions:event-severity-level "Info";
    dn-events-extensions:event-message-string "SZTP state changed to {new-state} on SZTP attempt on {server-address}:{port}";
    dn-events-extensions:event-corrective-action-string "No corrective action required unless state indicates an error.";
    dn-events-extensions:event-trigger-component-string "SZTP Client";
    dn-events-extensions:event-group "Management";
    leaf new-state {
      type string;
      description
        "The new state of the SZTP provisioning process.";
    }
    leaf server-address {
      type string;
      description
        "Address of the SZTP bootstrap server";
    }
    leaf port {
      type uint16;
      description
        "Port of the SZTP bootstrap server";
    }
  }

  notification SZTP_ATTEMPT_FAILED {
    description
      "The SZTP provisioning flow has failed.";
    dn-events-extensions:event-severity-level "Warning";
    dn-events-extensions:event-message-string "SZTP flow encountered a failure on SZTP attempt on {server-address}:{port}. error: {error-message}";
    dn-events-extensions:event-corrective-action-string "Check the logs for detailed error information and take remedial actions.";
    dn-events-extensions:event-trigger-component-string "SZTP Client";
    dn-events-extensions:event-group "Management";
    leaf server-address {
      type string;
      description
        "Address of the SZTP bootstrap server";
    }
    leaf port {
      type uint16;
      description
        "Port of the SZTP bootstrap server";
    }
    leaf error-message {
      type string;
      description
        "Error description";
    }
  }

  notification SZTP_FLOW_COMPLETED {
    description
      "The SZTP provisioning flow has completed successfully.";
    dn-events-extensions:event-severity-level "Info";
    dn-events-extensions:event-message-string "SZTP flow completed successfully from onboarding information recieved from {server-address}:{port}";
    dn-events-extensions:event-corrective-action-string "No corrective action required.";
    dn-events-extensions:event-trigger-component-string "SZTP Client";
    dn-events-extensions:event-group "Management";
    leaf server-address {
      type string;
      description
        "Address of the SZTP bootstrap server";
    }
    leaf port {
      type uint16;
      description
        "Port of the SZTP bootstrap server";
    }
  }

  notification SZTP_RESTORE_START {
    description
      "Initiates a restoration process for SZTP to revert system configurations and os version to pre-SZTP flow settings, after an interrupted or failed SZTP flow.";
    dn-events-extensions:event-severity-level "Info";
    dn-events-extensions:event-message-string "Restoring to initial state after interrupted or failed SZTP Flow from onboarding information recieved from {server-address}:{port}";
    dn-events-extensions:event-corrective-action-string "No corrective action.";
    dn-events-extensions:event-trigger-component-string "SZTP Client";
    dn-events-extensions:event-group "Management";
    leaf server-address {
      type string;
      description
        "Address of the SZTP bootstrap server";
    }
    leaf port {
      type uint16;
      description
        "Port of the SZTP bootstrap server ";
    }
  }

  notification SZTP_RESTORE_FAILED {
    description
      "The SZTP restoration process encountered a failure, which may require manual investigation and intervention.";
    dn-events-extensions:event-severity-level "Error";
    dn-events-extensions:event-message-string "SZTP restoration operation failed after interrupted or failed SZTP Flow from onboarding information recieved from {server-address}:{port}. error:{error}";
    dn-events-extensions:event-corrective-action-string "Investigate the cause of the restoration failure and execute necessary troubleshooting steps.";
    dn-events-extensions:event-trigger-component-string "SZTP Client";
    dn-events-extensions:event-group "Management";
    leaf server-address {
      type string;
      description
        "Address of the SZTP bootstrap server";
    }
    leaf port {
      type uint16;
      description
        "Port of the SZTP bootstrap server ";
    }
    leaf error {
      type string;
      description
        "Error message of the restoration process failure.";
    }
  }

  notification SZTP_RESTORE_COMPLETED {
    description
      "Indicates the successful completion of the SZTP restoration process, confirming that the system's configurations and state are reverted to the initial state before SZTP flow.";
    dn-events-extensions:event-severity-level "Info";
    dn-events-extensions:event-message-string "SZTP restoration operation completed successfully after interrupted or failed SZTP Flow from onboarding information recieved from {server-address}:{port}.";
    dn-events-extensions:event-corrective-action-string "No further action is required.";
    dn-events-extensions:event-trigger-component-string "SZTP Client";
    dn-events-extensions:event-group "Management";
    leaf server-address {
      type string;
      description
        "Address of the SZTP bootstrap server";
    }
    leaf port {
      type uint16;
      description
        "Port of the SZTP bootstrap server ";
    }
  }

  notification SZTP_SERVER_CONFIG {
    description
      "The SZTP server configuration has changed.";
    dn-events-extensions:event-severity-level "Info";
    dn-events-extensions:event-message-string "User {user-name} has {action} the SZTP bootstrap server configuration for server {server-address}:{port}.";
    dn-events-extensions:event-corrective-action-string "No further action is required.";
    dn-events-extensions:event-trigger-component-string "Transaction-manager";
    dn-events-extensions:event-group "Management";
    leaf server-address {
      type string;
      description
        "Address of the SZTP bootstrap server";
    }
    leaf port {
      type uint16;
      description
        "Port of the SZTP bootstrap server ";
    }
    leaf action {
      type string;
      description
        "Action taken on the SZTP server configuration (e.g., added, updated, removed).";
    }
    leaf user-name {
      type string;
      description
        "Username of the person who changed the configuration.";
    }
  }

  notification SZTP_GLOBAL_CONFIG {
    description
      "The SZTP global configuration has changed.";
    dn-events-extensions:event-severity-level "Info";
    dn-events-extensions:event-message-string "User {user-name} has {action} the SZTP global configuration";
    dn-events-extensions:event-corrective-action-string "No further action is required.";
    dn-events-extensions:event-trigger-component-string "Transaction-manager";
    dn-events-extensions:event-group "Management";
    leaf action {
      type string;
      description
        "Action taken on the SZTP global configuration (e.g., updated, reset).";
    }
    leaf user-name {
      type string;
      description
        "Username of the person who changed the global configuration.";
    }
  }

  // TACACS events

  notification TACACS_AUTHENTICATION_REJECTED {
    description
      "User authentication was rejected by TACACS server.";
    dn-events-extensions:event-severity-level "Info";
    dn-events-extensions:event-message-string "User {user-name} authentication has been rejected by TACACS server {server-address}:{port} ({vrf-name}) with the message {server-message}";
    dn-events-extensions:event-corrective-action-string "This is informational, no corrective action required.";
    dn-events-extensions:event-trigger-component-string "CLI";
    dn-events-extensions:event-group "AAA";
    leaf user-name {
      type string;
      description
        "Username that was sent to the server";
    }
    leaf server-address {
      type string;
      description
        "Server address - an IP address or a hostname";
    }
    leaf port {
      type uint16;
      description
        "Server port";
    }
    leaf vrf-name {
      type string;
      description
        "Server vrf name";
    }
    leaf server-message {
      type string;
      description
        "Message received from the server, can be empty";
    }
  }

  notification TACACS_AUTHORIZATION_DENIED {
    description
      "User authorization was denied by TACACS server.";
    dn-events-extensions:event-severity-level "Info";
    dn-events-extensions:event-message-string "User {user-name} authorization has been denied by TACACS server {server-address}:{port} ({vrf-name}) with the message {server-message}";
    dn-events-extensions:event-corrective-action-string "This is informational, no corrective action required.";
    dn-events-extensions:event-trigger-component-string "CLI";
    dn-events-extensions:event-group "AAA";
    leaf user-name {
      type string;
      description
        "Username that was sent to the server";
    }
    leaf server-address {
      type string;
      description
        "Server address - an IP address or a hostname";
    }
    leaf port {
      type uint16;
      description
        "Server port";
    }
    leaf vrf-name {
      type string;
      description
        "Server vrf name";
    }
    leaf server-message {
      type string;
      description
        "Message received from the server, can be empty";
    }
  }

  notification TACACS_COMMAND_AUTHORIZATION_DENIED {
    description
      "User CLI command authorization was denied by TACACS server.";
    dn-events-extensions:event-severity-level "Info";
    dn-events-extensions:event-message-string "User {user-name} CLI command {cli-command}, authorization has been denied by TACACS server {server-address}:{port} ({vrf-name}) with the message {server-message}";
    dn-events-extensions:event-corrective-action-string "This is informational, no corrective action required.";
    dn-events-extensions:event-trigger-component-string "CLI";
    dn-events-extensions:event-group "AAA";
    leaf user-name {
      type string;
      description
        "Username that was sent to the server";
    }
    leaf server-address {
      type string;
      description
        "Server address - an IP address or a hostname";
    }
    leaf port {
      type uint16;
      description
        "Server port";
    }
    leaf vrf-name {
      type string;
      description
        "Server vrf name";
    }
    leaf server-message {
      type string;
      description
        "Message received from the server, can be empty";
    }
    leaf cli-command {
      type string;
      description
        "the cli command that was sent to the server";
    }
  }

  notification TACACS_ACCOUNTING_FAILED {
    description
      "The TACACS accounting was rejected by the AAA server.";
    dn-events-extensions:event-severity-level "Error";
    dn-events-extensions:event-message-string "Accounting has been rejected by the AAA server {server-address}:{port} ({vrf-name})";
    dn-events-extensions:event-corrective-action-string "Restore connectivity to TACACS server or configure an alternative TACACS server.";
    dn-events-extensions:event-trigger-component-string "CLI";
    dn-events-extensions:event-group "Management";
    leaf server-address {
      type string;
      description
        "Server address - an IP address or a hostname";
    }
    leaf port {
      type uint16;
      description
        "Server port";
    }
    leaf vrf-name {
      type string;
      description
        "Server vrf name";
    }
  }

  notification RADIUS_AUTHENTICATION_REJECTED {
    description
      "User authentication was rejected by RADIUS server.";
    dn-events-extensions:event-severity-level "Info";
    dn-events-extensions:event-message-string "User {user-name} authentication has been rejected by RADIUS server {server-address}:{port} ({vrf-name}) with the message {server-message}";
    dn-events-extensions:event-corrective-action-string "This is informational, no corrective action required.";
    dn-events-extensions:event-trigger-component-string "CLI";
    dn-events-extensions:event-group "AAA";
    leaf user-name {
      type string;
      description
        "Username that was sent to the server";
    }
    leaf server-address {
      type string;
      description
        "Server address - an IP address or a hostname";
    }
    leaf port {
      type uint16;
      description
        "Server port";
    }
    leaf vrf-name {
      type string;
      description
        "Server vrf name";
    }
    leaf server-message {
      type string;
      description
        "Message received from the server, can be empty";
    }
  }

  notification TACACS_SERVER_CONFIG {
    description
      "The user indicated has changed the TACACS server configuration.";
    dn-events-extensions:event-severity-level "Info";
    dn-events-extensions:event-message-string "User {user-name} has {action} TACACS server {server-address}:{port} ({vrf-name}) configuration";
    dn-events-extensions:event-corrective-action-string "This is informational, no corrective action required.";
    dn-events-extensions:event-trigger-component-string "Transaction-manager";
    dn-events-extensions:event-group "Management";
    leaf server-address {
      type string;
      description
        "Server address - an IP address or a hostname";
    }
    leaf port {
      type uint16;
      description
        "Server port";
    }
    leaf vrf-name {
      type string;
      description
        "Server vrf name";
    }
    leaf action {
      type string;
      description
        "TACACS server configuration action (added/removed server)";
    }
    leaf user-name {
      type string;
      description
        "System user-name";
    }
  }

  notification AAA_CONFIG_AUTHENTICATION_ORDER_CHANGED {
    description
      "The user has configured the AAA authentication-order configuration.";
    dn-events-extensions:event-severity-level "Info";
    dn-events-extensions:event-message-string "User {user-name} has configured AAA authentication order type to {authentication-order-type}";
    dn-events-extensions:event-corrective-action-string "This is informational, no corrective action required.";
    dn-events-extensions:event-trigger-component-string "Transaction-manager";
    dn-events-extensions:event-group "Management";
    leaf authentication-order-type {
      type string;
      description
        "AAA authentication order type configuration ";
    }
    leaf user-name {
      type string;
      description
        "System user-name";
    }
  }

  notification AAA_CONFIG_FALLBACK_ON_REJECT_CHANGED {
    description
      "The user has configured the AAA fallback-on-reject configuration.";
    dn-events-extensions:event-severity-level "Info";
    dn-events-extensions:event-message-string "User {user-name} has configured AAA fallback-on-reject state to {fallback-on-reject-state}";
    dn-events-extensions:event-corrective-action-string "This is informational, no corrective action required.";
    dn-events-extensions:event-trigger-component-string "Transaction-manager";
    dn-events-extensions:event-group "Management";
    leaf fallback-on-reject-state {
      type string;
      description
        "AAA fallback-on-reject state configuration ";
    }
    leaf user-name {
      type string;
      description
        "System user-name";
    }
  }

  notification TACACS_AUTHORIZATION_TYPE_CONFIG {
    description
      "The user has configured the TACACS authorization type configuration.";
    dn-events-extensions:event-severity-level "Info";
    dn-events-extensions:event-message-string "User {user-name} has configured TACACS autherization type to {authorization-type}";
    dn-events-extensions:event-corrective-action-string "This is informational, no corrective action required.";
    dn-events-extensions:event-trigger-component-string "Transaction-manager";
    dn-events-extensions:event-group "Management";
    leaf authorization-type {
      type string;
      description
        "TACACS authorization type configuration ";
    }
    leaf user-name {
      type string;
      description
        "System user-name";
    }
  }

  notification RADIUS_SERVER_CONFIG {
    description
      "The user indicated has changed the RADIUS server configuration.";
    dn-events-extensions:event-severity-level "Info";
    dn-events-extensions:event-message-string "User {user-name} has {action} RADIUS server {server-address}:{port} ({vrf-name}) configuration";
    dn-events-extensions:event-corrective-action-string "This is informational, no corrective action required.";
    dn-events-extensions:event-trigger-component-string "Transaction-manager";
    dn-events-extensions:event-group "Management";
    leaf server-address {
      type string;
      description
        "Server address - an IP address or a hostname";
    }
    leaf port {
      type uint16;
      description
        "Server port";
    }
    leaf vrf-name {
      type string;
      description
        "Server vrf name";
    }
    leaf action {
      type string;
      description
        "RADIUS server configuration action (added/removed server)";
    }
    leaf user-name {
      type string;
      description
        "System user-name";
    }
  }

  notification RADIUS_AUTHORIZATION_DENIED {
    description
      "User authorization was denied by RADIUS server.";
    dn-events-extensions:event-severity-level "Info";
    dn-events-extensions:event-message-string "User {user-name} authorization has been denied by RADIUS server {server-address}:{port} ({vrf-name}) with the message {server-message}";
    dn-events-extensions:event-corrective-action-string "This is informational, no corrective action required.";
    dn-events-extensions:event-trigger-component-string "CLI";
    dn-events-extensions:event-group "AAA";
    leaf user-name {
      type string;
      description
        "Username that was sent to the server";
    }
    leaf server-address {
      type string;
      description
        "Server address - an IP address or a hostname";
    }
    leaf port {
      type uint16;
      description
        "Server port";
    }
    leaf vrf-name {
      type string;
      description
        "Server vrf name";
    }
    leaf server-message {
      type string;
      description
        "Message received from the server, can be empty";
    }
  }

  notification RADIUS_AUTHORIZATION_DEGRADED_MODE {
    description
      "User authorization missing VSA data, session authorized in degraded mode.";
    dn-events-extensions:event-severity-level "Info";
    dn-events-extensions:event-message-string "User {user-name} authorization is missing VSA data connected as viewer, RADIUS server {server-address}:{port} ({vrf-name}) with the message {server-message}";
    dn-events-extensions:event-corrective-action-string "Contact customer support.";
    dn-events-extensions:event-trigger-component-string "CLI";
    dn-events-extensions:event-group "AAA";
    leaf user-name {
      type string;
      description
        "Username that was sent to the server";
    }
    leaf server-address {
      type string;
      description
        "Server address - an IP address or a hostname";
    }
    leaf port {
      type uint16;
      description
        "Server port";
    }
    leaf vrf-name {
      type string;
      description
        "Server vrf name";
    }
    leaf server-message {
      type string;
      description
        "Message received from the server, can be empty";
    }
  }

  notification TACACS_SERVER_STATE_CHANGE_NOT_AVAILABLE {
    description
      "DNOS failed to connect to the listed TACACS server, the TACACS server is not available.";
    dn-events-extensions:event-severity-level "Warning";
    dn-events-extensions:event-message-string "DNOS has failed to connect to a TACACS server {server-address}:{port} ({vrf-name}) with {function} due to {reason}, TACACS server is not available.";
    dn-events-extensions:event-corrective-action-string "Check TACACS server status and availability.";
    dn-events-extensions:event-trigger-component-string "CLI";
    dn-events-extensions:event-group "AAA";
    leaf server-address {
      type string;
      description
        "Server address - an IP address or a hostname";
    }
    leaf port {
      type uint16;
      description
        "Server port";
    }
    leaf vrf-name {
      type string;
      description
        "Server vrf name";
    }
    leaf reason {
      type string;
      description
        "Reason for the connectivity failure with a server
         (e.g. connectivity problems, parsing errors, wrong credentials, other)";
    }
    leaf function {
      type string;
      description
        "Function for which system event was generated - authentication, authorization or accounting";
    }
  }

  notification RADIUS_SERVER_STATE_CHANGE_NOT_AVAILABLE {
    description
      "DNOS failed to connect to the listed RADIUS server, the RADIUS server is not available.";
    dn-events-extensions:event-severity-level "Warning";
    dn-events-extensions:event-message-string "DNOS has failed to connect to RADIUS server {server-address}:{port} ({vrf-name}) due to {reason}, RADIUS server is not available.";
    dn-events-extensions:event-corrective-action-string "Check RADIUS server status and availability.";
    dn-events-extensions:event-trigger-component-string "CLI";
    dn-events-extensions:event-group "AAA";
    leaf server-address {
      type string;
      description
        "Server address - an IP address or a hostname";
    }
    leaf port {
      type uint16;
      description
        "Server port";
    }
    leaf vrf-name {
      type string;
      description
        "Server vrf name";
    }
    leaf reason {
      type string;
      description
        "reason for the connectivity failure with a server
         (e.g. connectivity problems, parsing errros, wrong credentials, other)";
    }
  }

  notification AAA_REMOTE_HOLDDOWN_START {
    description
      "DNOS failed to contact remote AAA servers, will perform AAA locally until remote AAA hold-down timer expires.";
    dn-events-extensions:event-severity-level "Warning";
    dn-events-extensions:event-message-string "All the {protocol} {function} servers are not available, DNOS will perform AAA locally.";
    dn-events-extensions:event-corrective-action-string "Check AAA servers status and availability.";
    dn-events-extensions:event-trigger-component-string "CLI";
    dn-events-extensions:event-group "AAA";
    leaf protocol {
      type string;
      description
        "Protocol that caused remote AAA hold-down - RADIUS or TACACS";
    }
    leaf function {
      type string;
      description
        "Function that caused remote AAA hold-down - authentication, authorization or accounting";
    }
  }

  notification TACACS_SERVER_STATE_CHANGE_ACTIVE {
    description
      "DNOS connected to the listed TACACS server and the TACACS server is now active.";
    dn-events-extensions:event-severity-level "Info";
    dn-events-extensions:event-message-string "Succeeded to connect to TACACS server {server-address}:{port} ({vrf-name}) with {function}, TACACS server is now active";
    dn-events-extensions:event-corrective-action-string "This is informational, no corrective action required.";
    dn-events-extensions:event-trigger-component-string "CLI";
    dn-events-extensions:event-group "AAA";
    leaf server-address {
      type string;
      description
        "Server address - an IP address or a hostname";
    }
    leaf port {
      type uint16;
      description
        "Server port";
    }
    leaf vrf-name {
      type string;
      description
        "Server vrf name";
    }
    leaf function {
      type string;
      description
        "Function for which system event was generated - authentication, authorization or accounting";
    }
  }

  notification RADIUS_SERVER_STATE_CHANGE_ACTIVE {
    description
      "DNOS connected to the listed RADIUS server and the RADIUS server is now active.";
    dn-events-extensions:event-severity-level "Info";
    dn-events-extensions:event-message-string "Succeeded to connect to RADIUS server {server-address}:{port} ({vrf-name}), the server is now active";
    dn-events-extensions:event-corrective-action-string "This is informational, no corrective action required.";
    dn-events-extensions:event-trigger-component-string "CLI";
    dn-events-extensions:event-group "AAA";
    leaf server-address {
      type string;
      description
        "Server address - an IP address or a hostname";
    }
    leaf port {
      type uint16;
      description
        "Server port";
    }
    leaf vrf-name {
      type string;
      description
        "Server vrf name";
    }
  }

  notification LDAP_SERVER_CONFIG {
    description
      "The user indicated has changed the LDAP server configuration.";
    dn-events-extensions:event-severity-level "Info";
    dn-events-extensions:event-message-string "User {user-name} has {action} LDAP server {server-address} on vrf {vrf-name} configuration";
    dn-events-extensions:event-corrective-action-string "This is informational, no corrective action required.";
    dn-events-extensions:event-trigger-component-string "Transaction-manager";
    dn-events-extensions:event-group "Management";
    leaf server-address {
      type string;
      description
        "Server address, can be set as an IP address or as a hostname";
    }
    leaf action {
      type string;
      description
        "LDAP server configuration action (added/removed server)";
    }
    leaf user-name {
      type string;
      description
        "System user-name";
    }
    leaf vrf-name {
      type string;
      description
        "Defines whether the server is in-band or out-of-band";
    }
  }

  notification LDAP_SERVER_STATE_CHANGE_NOT_AVAILABLE {
    description
      "DNOS failed to connect to the listed LDAP server, the LDAP server is not available.";
    dn-events-extensions:event-severity-level "Warning";
    dn-events-extensions:event-message-string "DNOS has failed to connect to a LDAP server {server-address} on VRF {vrf-name} due to {reason}, LDAP server is not available.";
    dn-events-extensions:event-corrective-action-string "Check LDAP server status and availability.";
    dn-events-extensions:event-trigger-component-string "Netconf";
    dn-events-extensions:event-group "Management";
    leaf server-address {
      type string;
      description
        "Server address, can be set as an IP address or as a hostname";
    }
    leaf reason {
      type string;
      description
        "Reason for the connectivity failure with a server
         (e.g. connectivity problems, parsing errors, wrong credentials, other)";
    }
    leaf vrf-name {
      type string;
      description
        "the vrf in which event happened";
    }
  }

  notification LDAP_SERVER_STATE_CHANGE_ACTIVE {
    description
      "DNOS connected to the listed LDAP server and the LDAP server is now active.";
    dn-events-extensions:event-severity-level "Info";
    dn-events-extensions:event-message-string "Succeeded to connect to LDAP server {server-address} on VRF {vrf-name}, LDAP server is now active";
    dn-events-extensions:event-corrective-action-string "This is informational, no corrective action required.";
    dn-events-extensions:event-trigger-component-string "Netconf";
    dn-events-extensions:event-group "Management";
    leaf server-address {
      type string;
      description
        "Server address, can be set as an IP address or as a hostname";
    }
    leaf vrf-name {
      type string;
      description
        "the vrf in which event happened";
    }
  }

  notification NETCONF_DYNAMIC_NACM_FALLBACK_TO_STATIC {
    description
      "Netconf failed to load dynamic NACM rules - fallback to static NACM.";
    dn-events-extensions:event-severity-level "Warning";
    dn-events-extensions:event-message-string "Netconf failed to load dynamic NACM rules - fallback to static NACM";
    dn-events-extensions:event-corrective-action-string "This is informational, no corrective action required.";
    dn-events-extensions:event-trigger-component-string "Netconf";
    dn-events-extensions:event-group "Management";
  }

  notification LDAP_AUTHORIZATION_DENIED {
    description
      "User authorization was denied by LDAP server.";
    dn-events-extensions:event-severity-level "Warning";
    dn-events-extensions:event-message-string "Dynamic NACM group {nacm-group} is not found in LDAP server. User {user-name} is denied";
    dn-events-extensions:event-corrective-action-string "This is informational, no corrective action required.";
    dn-events-extensions:event-trigger-component-string "Netconf";
    dn-events-extensions:event-group "Management";
    leaf user-name {
      type string;
      description
        "Username that was sent to the server";
    }
    leaf nacm-group {
      type string;
      description
        "NACM groups recived from the server";
    }
  }

  notification LDAP_REMOTE_HOLDDOWN_START {
    description
      "DNOS failed to contact remote LDAP servers, will perform LDAP locally until remote LDAP hold-down timer expires.";
    dn-events-extensions:event-severity-level "Warning";
    dn-events-extensions:event-message-string "All the LDAP servers are not available.";
    dn-events-extensions:event-corrective-action-string "Check LDAP servers status and availability.";
    dn-events-extensions:event-trigger-component-string "Netconf";
    dn-events-extensions:event-group "Management";
  }

  // Techsupport events

  notification TECHSUPPORT_FILE_CREATION_STOPPED {
    description
      "The creation of techsupport file had stopped";
    dn-events-extensions:event-severity-level "Warning";
    dn-events-extensions:event-message-string "Techsupport file {filename} requested by user {user-name} at {timestamp} was not created because of {reason}";
    dn-events-extensions:event-corrective-action-string "In case of file size problem, use the available filters to reduce the amount of collected information.";
    dn-events-extensions:event-trigger-component-string "CLI";
    dn-events-extensions:event-group "System";
    leaf filename {
      type string;
      description
        "the name of the techsupport file requested to be created";
    }
    leaf user-name {
      type string;
      description
        "System user-name";
    }
    leaf timestamp {
      type string;
      description
        "date and time of when techsupport file was requrested";
    }
    leaf reason {
      type string;
      description
        "Reason for why techsupport file creation had stopped";
    }
  }

  // Transactions events

  notification TRANSACTION_COMMIT_REQUEST {
    description
      "A new configuration request was committed by the user listed.";
    dn-events-extensions:event-severity-level "Notice";
    dn-events-extensions:event-message-string "User {user-name} requested {command-type} operation";
    dn-events-extensions:event-corrective-action-string "This is informational, no corrective action required.";
    dn-events-extensions:event-trigger-component-string "Transaction-manager";
    dn-events-extensions:event-group "Management";
    leaf user-name {
      type string;
      description
        "System user-name";
    }
    leaf command-type {
      type string;
      description
        "Commit command type (i.e commit no-warning)";
    }
  }

  notification TRANSACTION_COMMIT_SUCCEEDED {
    description
      "A new configuration was committed successfully by the user listed.";
    dn-events-extensions:event-severity-level "Info";
    dn-events-extensions:event-message-string "User {user-name} successfully committed configuration {commit-id}";
    dn-events-extensions:event-corrective-action-string "This is informational, no corrective action required.";
    dn-events-extensions:event-trigger-component-string "Transaction-manager";
    dn-events-extensions:event-group "Management";
    leaf user-name {
      type string;
      description
        "System user-name";
    }
    leaf commit-id {
      type uint16;
      description
        "Commit ID";
    }
  }

  notification TRANSACTION_COMMIT_CONFIRM {
    description
      "A new configuration was committed using commit confirm operation. If the configuration is not confirmed within the indicated number of minutes, the configuration will rollback automatically.";
    dn-events-extensions:event-severity-level "Info";
    dn-events-extensions:event-message-string "User {user-name} successfully committed configuration {commit-id} using commit-confirm operation waiting {confirm-time} minutes ";
    dn-events-extensions:event-corrective-action-string "Confirm the commit or wait for auto revert.";
    dn-events-extensions:event-trigger-component-string "Transaction-manager";
    dn-events-extensions:event-group "Management";
    leaf user-name {
      type string;
      description
        "System user-name";
    }
    leaf commit-id {
      type uint16;
      description
        "Commit ID";
    }
    leaf confirm-time {
      type uint16;
      description
        "Confirm time in minutes";
    }
  }

  notification TRANSACTION_COMMIT_FAILED {
    description
      "A new configuration was committed, but the commit has failed.";
    dn-events-extensions:event-severity-level "Error";
    dn-events-extensions:event-message-string "User {user-name} committed configuration {commit-id}. However, configuration commit has failed";
    dn-events-extensions:event-corrective-action-string
      "When the commit fails, an error is displayed which specifies the line within the configuration that
       failed. Correct the configuration error and commit the configuration again. You may need to compare your current configuration to the failed configuration to understand why the commit failed.";
    dn-events-extensions:event-trigger-component-string "Transaction-manager";
    dn-events-extensions:event-group "Management";
    leaf user-name {
      type string;
      description
        "System user-name";
    }
    leaf commit-id {
      type uint16;
      description
        "Commit ID";
    }
  }

  notification TRANSACTION_COMMIT_CHECK_FAILED {
    description
      "There was an error while trying to check the candidate configuration.";
    dn-events-extensions:event-severity-level "Error";
    dn-events-extensions:event-message-string "User {user-name} committed commit check operation. However, configuration commit check has failed at {configuration-line}";
    dn-events-extensions:event-corrective-action-string
      "When the commit fails, an error is displayed which specifies the line within the configuration that
       failed. Correct the configuration error and commit the configuration again. You may need to compare your current configuration to the failed configuration to understand why the commit failed.";
    dn-events-extensions:event-trigger-component-string "Transaction-manager";
    dn-events-extensions:event-group "Management";
    leaf user-name {
      type string;
      description
        "System user-name";
    }
    leaf configuration-line {
      type string;
      description
        "First failed configuration-line";
    }
  }

  notification TRANSACTION_COMMIT_CHECK_SUCCEEDED {
    description
      "The commit check operation was performed successfully.";
    dn-events-extensions:event-severity-level "Info";
    dn-events-extensions:event-message-string "User {user-name} successfully performed commit check operation";
    dn-events-extensions:event-corrective-action-string "This is informational, no corrective action required.";
    dn-events-extensions:event-trigger-component-string "Transaction-manager";
    dn-events-extensions:event-group "Management";
    leaf user-name {
      type string;
      description
        "System user-name";
    }
  }

  notification TRANSACTION_COMMIT_STATE {
    description
      "The system commit transactions current state.";
    dn-events-extensions:event-severity-level "Info";
    dn-events-extensions:event-message-string "User {user-name} committed configuration {commit-id}. Transaction is at current state {transaction-state}";
    dn-events-extensions:event-corrective-action-string "This is informational, no corrective action required.";
    dn-events-extensions:event-trigger-component-string "Transaction-manager";
    dn-events-extensions:event-group "Management";
    leaf user-name {
      type string;
      description
        "System user-name";
    }
    leaf commit-id {
      type uint16;
      description
        "Commit ID";
    }
    leaf transaction-state {
      type string;
      description
        "Current transaction state";
    }
  }

  notification TRANSACTION_ROLLBACK_COMPLETED {
    description
      "The user listed completed a rollback to a previous configuration.";
    dn-events-extensions:event-severity-level "Info";
    dn-events-extensions:event-message-string "User {user-name} rollback configuration {commit-id} completed successfully";
    dn-events-extensions:event-corrective-action-string "This is informational, no corrective action required.";
    dn-events-extensions:event-trigger-component-string "Transaction-manager";
    dn-events-extensions:event-group "Management";
    leaf user-name {
      type string;
      description
        "System user-name";
    }
    leaf commit-id {
      type uint16;
      description
        "Commit ID";
    }
  }

  notification TRANSACTION_ROLLBACK_FAILED {
    description
      "The rollback to a previous configuration failed.";
    dn-events-extensions:event-severity-level "Info";
    dn-events-extensions:event-message-string "User {user-name} rollback configuration {commit-id} upload failed";
    dn-events-extensions:event-corrective-action-string "This is informational, no corrective action required.";
    dn-events-extensions:event-trigger-component-string "Transaction-manager";
    dn-events-extensions:event-group "Management";
    leaf user-name {
      type string;
      description
        "System user-name";
    }
    leaf commit-id {
      type uint16;
      description
        "Commit ID";
    }
  }

  // Timezone events

  notification SYSTEM_TIME_DST_START {
    description
      "The system time has changed to Daylight Saving Time. The system clock has moved one hour forward.";
    dn-events-extensions:event-severity-level "Info";
    dn-events-extensions:event-message-string "System time changed to Daylight Saving Time. Clock time is now in summer time and moved 1 hour forward";
    dn-events-extensions:event-corrective-action-string "This is informational, no corrective action required.";
    dn-events-extensions:event-trigger-component-string "Management";
    dn-events-extensions:event-group "Management";
  }

  notification SYSTEM_TIME_DST_END {
    description
      "The system time has changed as Daylight Saving Time has ended. The system clock has moved one hour back.";
    dn-events-extensions:event-severity-level "Info";
    dn-events-extensions:event-message-string "System time changed as Daylight Saving Time ended. Clock time is now in winter time and moved 1 hour back";
    dn-events-extensions:event-corrective-action-string "This is informational, no corrective action required.";
    dn-events-extensions:event-trigger-component-string "Management";
    dn-events-extensions:event-group "Management";
  }

  notification SYSTEM_TIMEZONE_CHANGE {
    description
      "User has changed the system timezone";
    dn-events-extensions:event-severity-level "Info";
    dn-events-extensions:event-message-string "User {user-name} modified system timezone to {timezone-name} {timezone-utc-offset}";
    dn-events-extensions:event-corrective-action-string "This is informational, no corrective action required.";
    dn-events-extensions:event-trigger-component-string "Management";
    dn-events-extensions:event-group "Management";
    leaf user-name {
      type string;
      description
        "System user-name";
    }
    leaf timezone-name {
      type string;
      description
        "timezone name, matching supported timezones in dn-timezone";
    }
    leaf timezone-utc-offset {
      type string;
      description
        "timezone offset from utc time. e.g UTC+2:00";
    }
  }

  // SSH events

  notification SSH_SESSION_LOGIN_DENIED {
    description
      "SSH has rejected a new session to the system due to client-list configuration.";
    dn-events-extensions:event-severity-level "Notice";
    dn-events-extensions:event-message-string "SSH login attempt from remote host {remote-host} on {vrf-name} has been rejected due to client-list configuration";
    dn-events-extensions:event-corrective-action-string "This is informational, no corrective action required.";
    dn-events-extensions:event-trigger-component-string "CLI";
    dn-events-extensions:event-group "Management";
    leaf remote-host {
      type string;
      description
        "Remote host address, can be an IP address or as hostname";
    }
    leaf vrf-name {
      description
        "the vrf in which event happened";
      type string;
    }
  }

  notification SSH_SESSION_LIMIT_CLEARED {
    description
      "The number of concurrent SSH sessions to the system is below the configured maximum number of connections.";
    dn-events-extensions:event-severity-level "Info";
    dn-events-extensions:event-message-string "Number of SSH sessions is below the configured maximum ({max-sessions})";
    dn-events-extensions:event-corrective-action-string "This is informational, no corrective action required.";
    dn-events-extensions:event-trigger-component-string "CLI";
    dn-events-extensions:event-group "Management";
    leaf max-sessions {
      type uint8;
      description
        "Maximum number of sessions";
    }
  }

  notification SSH_SESSION_LIMIT_REACHED {
    description
      "The number of concurrent SSH sessions to the system has reached the maximum number of sessions. No new SSH sessions can be established.";
    dn-events-extensions:event-severity-level "Warning";
    dn-events-extensions:event-message-string "Number of SSH sessions has reached the configured maximum ({max-sessions})";
    dn-events-extensions:event-corrective-action-string
      "<p>Terminate active SSH sessions to the system:</p>
       <ol>
       <li>Run command 'show system ssh sessions' to view the existing SSH sessions.</li>
       <li>Select a session-id for the connection you want to terminate.</li>
       <li>Run the command 'clear ssh session [session-id]'.</li>
       </ol>";
    dn-events-extensions:event-trigger-component-string "CLI";
    dn-events-extensions:event-group "Management";
    leaf max-sessions {
      type uint8;
      description
        "Maximum number of sessions";
    }
  }

  notification SSH_SESSION_CLOSED {
    description
      "The user indicated closed the SSH session via the remote host.";
    dn-events-extensions:event-severity-level "Info";
    dn-events-extensions:event-message-string "User {user-name} closed the SSH session {session-id} (remote host {remote-host} VRF {vrf-name}) ";
    dn-events-extensions:event-corrective-action-string "This is informational, no corrective action required.";
    dn-events-extensions:event-trigger-component-string "CLI";
    dn-events-extensions:event-group "Management";
    leaf user-name {
      type string;
      description
        "System user-name";
    }
    leaf remote-host {
      type string;
      description
        "Remote host address, can be an IP address or as hostname";
    }
    leaf session-id {
      type uint16;
      description
        "Session ID";
    }
    leaf vrf-name {
      description
        "the vrf in which event happened";
      type string;
    }
  }

  notification SSH_SESSION_LOGIN {
    description
      "The user and remote host indicated has logged into the system using SSH.";
    dn-events-extensions:event-severity-level "Info";
    dn-events-extensions:event-message-string "User {user-name} has logged in using SSH (remote host {remote-host} VRF {vrf-name}) ";
    dn-events-extensions:event-corrective-action-string "This is informational, no corrective action required.";
    dn-events-extensions:event-trigger-component-string "CLI";
    dn-events-extensions:event-group "Management";
    leaf user-name {
      type string;
      description
        "System user-name";
    }
    leaf remote-host {
      type string;
      description
        "Remote host address, can be an IP address or as hostname";
    }
    leaf vrf-name {
      description
        "the vrf in which event happened";
      type string;
    }
  }

  notification SSH_SESSION_TERMINATED {
    description
      "The SSH session to system was terminated by the user indicated using the command 'clear ssh session'.";
    dn-events-extensions:event-severity-level "Notice";
    dn-events-extensions:event-message-string "SSH session {session-id} (remote host {remote-host} VRF {vrf-name}) terminated by user {user-name}";
    dn-events-extensions:event-corrective-action-string "No corrective action.";
    dn-events-extensions:event-trigger-component-string "CLI";
    dn-events-extensions:event-group "Management";
    leaf user-name {
      type string;
      description
        "System user-name";
    }
    leaf remote-host {
      type string;
      description
        "Remote host address, can be an IP address or as hostname";
    }
    leaf session-id {
      type uint16;
      description
        "Session ID";
    }
    leaf vrf-name {
      description
        "the vrf in which event happened";
      type string;
    }
  }

  notification SSH_SESSION_TIMEOUT {
    description
      "The SSH session to system was terminated by the system due to session inactivity.";
    dn-events-extensions:event-severity-level "Info";
    dn-events-extensions:event-message-string "SSH session {session-id} (remote host {remote-host} VRF {vrf-name}) was terminated due to timeout";
    dn-events-extensions:event-corrective-action-string "This is informational, no corrective action required.";
    dn-events-extensions:event-trigger-component-string "CLI";
    dn-events-extensions:event-group "Management";
    leaf remote-host {
      type string;
      description
        "Remote host address, can be an IP address or as hostname";
    }
    leaf session-id {
      type uint16;
      description
        "Session ID";
    }
    leaf vrf-name {
      description
        "the vrf in which event happened";
      type string;
    }
  }

  notification SSH_MAXIMUM_SESSION_LIMIT_REJECT {
    description
      "A new SSH session to the system was rejected since the number of concurrent SSH sessions has reached the configured limit.";
    dn-events-extensions:event-severity-level "Notice";
    dn-events-extensions:event-message-string "A new SSH session of user {user-name} from remote host {remote-host} has been rejected since the number of concurrent active SSH sessions has reached the configured limit of {max-sessions}";
    dn-events-extensions:event-corrective-action-string
      "<p>Terminate some active SSH sessions to the system:</p>
       <ol>
       <li>Run command 'show system ssh sessions' to view the existing SSH sessions.</li>
       <li>Select a session-id for the connection you want to terminate.</li>
       <li>Run the command 'clear ssh session [session-id]'.</li>
       </ol>";
    dn-events-extensions:event-trigger-component-string "CLI";
    dn-events-extensions:event-group "Management";
    leaf max-sessions {
      type uint8;
      description
        "Maximum number of sessions";
    }
    leaf user-name {
      type string;
      description
        "System user-name";
    }
    leaf remote-host {
      type string;
      description
        "Remote host address, can be an IP address or as hostname";
    }
  }

  notification SSH_SESSION_LOGIN_LOCKED {
    description
      "A new SSH session by the user indicated was rejected due to maximum number of login attempts. The user must wait for the holdoff period.";
    dn-events-extensions:event-severity-level "Notice";
    dn-events-extensions:event-message-string "Maximum number of login attempts ({login-attempts}) was reached by user {user-name}";
    dn-events-extensions:event-corrective-action-string "Wait for holdoff time defined by 'system login session-holdoff'.";
    dn-events-extensions:event-trigger-component-string "CLI";
    dn-events-extensions:event-group "Management";
    leaf user-name {
      type string;
      description
        "System user-name";
    }
    leaf login-attempts {
      type uint8;
      description
        "Maximum number of failed logins";
    }
  }

  notification SSH_SESSION_LOGIN_FAILED {
    description
      "The user login attempt was rejected due to incorrect credentials.";
    dn-events-extensions:event-severity-level "Info";
    dn-events-extensions:event-message-string "User {user-name} login attempt from remote host {remote-host} VRF {vrf-name} rejected due to incorrect credentials";
    dn-events-extensions:event-corrective-action-string "This is informational, no corrective action required.";
    dn-events-extensions:event-trigger-component-string "CLI";
    dn-events-extensions:event-group "Management";
    leaf user-name {
      type string;
      description
        "System user-name";
    }
    leaf remote-host {
      type string;
      description
        "Remote host address, can be an IP address or as hostname";
    }
    leaf vrf-name {
      description
        "the vrf in which event happened";
      type string;
    }
  }

  notification SSH_SESSION_TIMEOUT_CONFIG {
    description
      "The user indicated changed the SSH session timeout parameter.";
    dn-events-extensions:event-severity-level "Notice";
    dn-events-extensions:event-message-string "User {user-name} has changed SSH Session timeout parameter";
    dn-events-extensions:event-corrective-action-string "No corrective action.";
    dn-events-extensions:event-trigger-component-string "Transaction-manager";
    dn-events-extensions:event-group "Management";
    leaf user-name {
      type string;
      description
        "System user-name";
    }
  }

  notification SSH_CLIENT_SESSION_TERMINATED {
    description
      "The SSH client session was terminated by the user indicated using the command 'clear ssh session'.";
    dn-events-extensions:event-severity-level "Notice";
    dn-events-extensions:event-message-string "SSH client session {session-id} (remote host {remote-host} VRF {vrf-name}) was terminated by user {user-name}";
    dn-events-extensions:event-corrective-action-string "No corrective action.";
    dn-events-extensions:event-trigger-component-string "CLI";
    dn-events-extensions:event-group "Management";
    leaf user-name {
      type string;
      description
        "System user-name";
    }
    leaf remote-host {
      type string;
      description
        "Remote host address, can be an IP address or as hostname";
    }
    leaf session-id {
      type uint16;
      description
        "Session ID";
    }
    leaf vrf-name {
      description
        "the vrf in which event happened";
      type string;
    }
  }

  notification SSH_CLIENT_CONFIG {
    description
      "The user indicated changed the SSH client capability.";
    dn-events-extensions:event-severity-level "Info";
    dn-events-extensions:event-message-string "User {user-name} changed SSH client capability to {client-state}";
    dn-events-extensions:event-corrective-action-string "This is informational, no corrective action required.";
    dn-events-extensions:event-trigger-component-string "Transaction-manager";
    dn-events-extensions:event-group "Management";
    leaf client-state {
      type enumeration {
        enum enabled;
        enum disabled;
      }
      description
        "SSH client configuration state";
    }
    leaf user-name {
      type string;
      description
        "System user-name";
    }
  }

  notification SSH_SERVER_CONFIG {
    description
      "The user indicated changed the SSH server capability.";
    dn-events-extensions:event-severity-level "Info";
    dn-events-extensions:event-message-string "User {user-name} changed SSH server capability to {server-state} in VRF {vrf-name}";
    dn-events-extensions:event-corrective-action-string "This is informational, no corrective action required.";
    dn-events-extensions:event-trigger-component-string "Transaction-manager";
    dn-events-extensions:event-group "Management";
    leaf server-state {
      type enumeration {
        enum enabled;
        enum disabled;
      }
      description
        "SSH server configuration state";
    }
    leaf user-name {
      type string;
      description
        "System user-name";
    }
    leaf vrf-name {
      description
        "the vrf in which event happened";
      type string;
    }
  }

  notification SSH_SERVER_CLIENT_LIST_CONFIG {
    description
      "The list of restricted users for the SSH server was configured/updated.";
    dn-events-extensions:event-severity-level "Notice";
    dn-events-extensions:event-message-string "List of restricted users for SSH server was configured/updated in VRF {vrf-name}";
    dn-events-extensions:event-corrective-action-string "No corrective action.";
    dn-events-extensions:event-trigger-component-string "Transaction-manager";
    dn-events-extensions:event-group "Management";
    leaf vrf-name {
      description
        "the vrf in which event happened";
      type string;
    }
  }

  notification SSH_SECURITY_MACS_CONFIG {
    description
      "The list of MAC algorithms configured to be used by SSH and NETCONF servers have been updated.";
    dn-events-extensions:event-severity-level "Notice";
    dn-events-extensions:event-message-string "List of configured MAC algorithms used by SSH and Netconf servers was updated";
    dn-events-extensions:event-corrective-action-string "No corrective action.";
    dn-events-extensions:event-trigger-component-string "Management";
    dn-events-extensions:event-group "Management";
  }

  notification SSH_SECURITY_CIPHERS_CONFIG {
    description
      "The list of ciphers configured to be used by SSH and NETCONF servers have been updated.";
    dn-events-extensions:event-severity-level "Notice";
    dn-events-extensions:event-message-string "List of configured ciphers used by SSH and Netconf servers was updated";
    dn-events-extensions:event-corrective-action-string "No corrective action.";
    dn-events-extensions:event-trigger-component-string "Management";
    dn-events-extensions:event-group "Management";
  }

  notification SSH_SECURITY_HOSTKEY_ALGORITHMS_CONFIG {
    description
      "The list of host-Key algorithms configured to be used by SSH and NETCONF servers have been updated.";
    dn-events-extensions:event-severity-level "Notice";
    dn-events-extensions:event-message-string "List of configured host-Key algorithms used by SSH and Netconf servers was updated";
    dn-events-extensions:event-corrective-action-string "No corrective action.";
    dn-events-extensions:event-trigger-component-string "Management";
    dn-events-extensions:event-group "Management";
  }

  notification SSH_SECURITY_ACCEPTED_PUBLIC_KEY_ALGORITHMS_CONFIG {
    description
      "The list of accepted public key algorithms configured to be used by SSH and NETCONF servers have been updated.";
    dn-events-extensions:event-severity-level "Notice";
    dn-events-extensions:event-message-string "List of configured accepted public key algorithms used by SSH and Netconf servers was updated";
    dn-events-extensions:event-corrective-action-string "No corrective action.";
    dn-events-extensions:event-trigger-component-string "Management";
    dn-events-extensions:event-group "Management";
  }

  notification SSH_SECURITY_KEY_EXCHANGE_ALGORITHMS_CONFIG {
    description
      "The list of key exchange algorithms configured to be used by SSH and NETCONF servers have been updated.";
    dn-events-extensions:event-severity-level "Notice";
    dn-events-extensions:event-message-string "List of configured key exchange algorithms used by SSH and Netconf servers was updated";
    dn-events-extensions:event-corrective-action-string "No corrective action.";
    dn-events-extensions:event-trigger-component-string "Management";
    dn-events-extensions:event-group "Management";
  }

  // FTP events

  notification FTP_MAXIMUM_SESSIONS_LIMIT_CLEARED {
    description
      "The number of concurrent FTP sessions to the system is below the configured maximum number of connections.";
    dn-events-extensions:event-severity-level "Info";
    dn-events-extensions:event-message-string "Number of FTP sessions is below the configured maximum ({max-sessions})";
    dn-events-extensions:event-corrective-action-string "This is informational, no corrective action required.";
    dn-events-extensions:event-trigger-component-string "Management";
    dn-events-extensions:event-group "Management";
    leaf max-sessions {
      type uint8;
      description
        "Maximum number of sessions";
    }
  }

  notification FTP_MAXIMUM_SESSIONS_LIMIT_REACHED {
    description
      "The number of concurrent FTP sessions to the system has reached the maximum number of sessions. No new FTP sessions can be established.";
    dn-events-extensions:event-severity-level "Warning";
    dn-events-extensions:event-message-string "Number of FTP sessions has reached the configured maximum ({max-sessions})";
    dn-events-extensions:event-corrective-action-string
      "<p>Terminate active FTP sessions to the system:</p>
       <ol>
       <li>Run command 'show system ftp sessions' to view the existing FTP sessions.</li>
       <li>Select a session-id for the connection you want to terminate.</li>
       <li>Run the command 'clear ftp session [session-id]'.</li>
       </ol>";
    dn-events-extensions:event-trigger-component-string "Management";
    dn-events-extensions:event-group "Management";
    leaf max-sessions {
      type uint8;
      description
        "Maximum number of sessions";
    }
  }

  notification FTP_SESSION_CLOSED {
    description
      "The user indicated closed the FTP session via the remote host.";
    dn-events-extensions:event-severity-level "Info";
    dn-events-extensions:event-message-string "user {user-name} closed the FTP session {session-id} (remote host {remote-host})";
    dn-events-extensions:event-corrective-action-string "This is informational, no corrective action required.";
    dn-events-extensions:event-trigger-component-string "Management";
    dn-events-extensions:event-group "Management";
    leaf user-name {
      type string;
      description
        "System user-name";
    }
    leaf remote-host {
      type string;
      description
        "Remote host address, can be an IP address or as hostname";
    }
    leaf session-id {
      type uint16;
      description
        "Session id";
    }
  }

  notification FTP_SESSION_LOGIN {
    description
      "The user and remote host indicated has logged into the system using FTP.";
    dn-events-extensions:event-severity-level "Info";
    dn-events-extensions:event-message-string "user {user-name} has logged in using FTP (remote host {remote-host})";
    dn-events-extensions:event-corrective-action-string "This is informational, no corrective action required.";
    dn-events-extensions:event-trigger-component-string "Management";
    dn-events-extensions:event-group "Management";
    leaf user-name {
      type string;
      description
        "System user-name";
    }
    leaf remote-host {
      type string;
      description
        "Remote host address, can be an IP address or as hostname";
    }
  }

  notification FTP_SESSION_TERMINATED {
    description
      "The FTP session to system was terminated by the user indicated using the command 'clear ftp session'.";
    dn-events-extensions:event-severity-level "Notice";
    dn-events-extensions:event-message-string "FTP session {session-id} (remote host {remote-host}) terminated by user {user-name}";
    dn-events-extensions:event-corrective-action-string "No corrective action.";
    dn-events-extensions:event-trigger-component-string "Management";
    dn-events-extensions:event-group "Management";
    leaf user-name {
      type string;
      description
        "System user-name";
    }
    leaf remote-host {
      type string;
      description
        "Remote host address, can be an IP address or as hostname";
    }
    leaf session-id {
      type uint16;
      description
        "Session id";
    }
  }

  notification FTP_IDLE_SESSION_TIMEOUT {
    description
      "The FTP session to system was terminated by the server due to session inactivity.";
    dn-events-extensions:event-severity-level "Info";
    dn-events-extensions:event-message-string "FTP session {session-id} (remote host {remote-host}) was terminated due to idle timeout";
    dn-events-extensions:event-corrective-action-string "This is informational, no corrective action required.";
    dn-events-extensions:event-trigger-component-string "Management";
    dn-events-extensions:event-group "Management";
    leaf remote-host {
      type string;
      description
        "Remote host address, can be an IP address or as hostname";
    }
    leaf session-id {
      type uint16;
      description
        "Session id";
    }
  }

  notification FTP_DATA_CONNECTION_TIMEOUT {
    description
      "The FTP session to system was terminated by the server due to session data stall timeout.";
    dn-events-extensions:event-severity-level "Info";
    dn-events-extensions:event-message-string "FTP session {session-id} (remote host {remote-host}) was terminated due to data timeout";
    dn-events-extensions:event-corrective-action-string "This is informational, no corrective action required.";
    dn-events-extensions:event-trigger-component-string "Management";
    dn-events-extensions:event-group "Management";
    leaf remote-host {
      type string;
      description
        "Remote host address, can be an IP address or as hostname";
    }
    leaf session-id {
      type uint16;
      description
        "Session id";
    }
  }

  notification FTP_MAXIMUM_SESSIONS_LIMIT_REJECT {
    description
      "A new FTP session to the system was rejected since the number of concurrent FTP sessions has reached the configured limit.";
    dn-events-extensions:event-severity-level "Notice";
    dn-events-extensions:event-message-string "A new FTP session from remote host {remote-host} has been rejected since the number of concurrent active FTP sessions has reached the configured limit of {max-sessions}";
    dn-events-extensions:event-corrective-action-string
      "<p>Terminate some active FTP sessions to the system:</p>
       <ol>
       <li>Run command 'show system ftp sessions' to view the existing FTP sessions.</li>
       <li>Select a session-id for the connection you want to terminate.</li>
       <li>Run the command 'clear ftp session [session-id]'.</li>
       </ol>";
    dn-events-extensions:event-trigger-component-string "Management";
    dn-events-extensions:event-group "Management";
    leaf max-sessions {
      type uint8;
      description
        "Maximum number of sessions";
    }
    leaf remote-host {
      type string;
      description
        "Remote host address, can be an IP address or as hostname";
    }
  }

  notification FTP_SESSION_LOGIN_FAILED {
    description
      "The user login attempt was rejected due to incorrect credentials.";
    dn-events-extensions:event-severity-level "Info";
    dn-events-extensions:event-message-string "User {user-name} login attempt from remote host {remote-host} rejected due to incorrect credentials";
    dn-events-extensions:event-corrective-action-string "This is informational, no corrective action required.";
    dn-events-extensions:event-trigger-component-string "Management";
    dn-events-extensions:event-group "Management";
    leaf user-name {
      type string;
      description
        "System user-name";
    }
    leaf remote-host {
      type string;
      description
        "Remote host address, can be an IP address or as hostname";
    }
  }

  notification FTP_IDLE_SESSION_TIMEOUT_CONFIG {
    description
      "The user indicated changed the FTP idle-session-timeout parameter.";
    dn-events-extensions:event-severity-level "Notice";
    dn-events-extensions:event-message-string "User {user-name} has changed FTP idle-session-timeout parameter";
    dn-events-extensions:event-corrective-action-string "No corrective action.";
    dn-events-extensions:event-trigger-component-string "Management";
    dn-events-extensions:event-group "Management";
    leaf user-name {
      type string;
      description
        "System user-name";
    }
  }

  notification FTP_DATA_CONNECTION_TIMEOUT_CONFIG {
    description
      "The user indicated changed the FTP data-connection-timeout parameter.";
    dn-events-extensions:event-severity-level "Notice";
    dn-events-extensions:event-message-string "User {user-name} has changed FTP data-connection-timeout parameter";
    dn-events-extensions:event-corrective-action-string "No corrective action.";
    dn-events-extensions:event-trigger-component-string "Management";
    dn-events-extensions:event-group "Management";
    leaf user-name {
      type string;
      description
        "System user-name";
    }
  }

  notification FTP_SERVER_ADMIN_STATE_CONFIG {
    description
      "The user indicated changed the FTP server admin-state.";
    dn-events-extensions:event-severity-level "Info";
    dn-events-extensions:event-message-string "User {user-name} changed FTP server admin-state to {server-state}";
    dn-events-extensions:event-corrective-action-string "This is informational, no corrective action required.";
    dn-events-extensions:event-trigger-component-string "Management";
    dn-events-extensions:event-group "Management";
    leaf server-state {
      type enumeration {
        enum enabled;
        enum disabled;
      }
      description
        "FTP server configuration state";
    }
    leaf user-name {
      type string;
      description
        "System user-name";
    }
  }

  notification FTP_SERVER_CLIENT_LIST_CONFIG {
    description
      "The list of restricted users for the FTP server was configured/updated.";
    dn-events-extensions:event-severity-level "Notice";
    dn-events-extensions:event-message-string "List of restricted users for FTP server was configured/updated";
    dn-events-extensions:event-corrective-action-string "No corrective action.";
    dn-events-extensions:event-trigger-component-string "Management";
    dn-events-extensions:event-group "Management";
  }

  notification FTP_SESSION_LOGIN_DENIED {
    description
      "A login attemp was rejected because the client appears as blocked at the client-list.";
    dn-events-extensions:event-severity-level "Notice";
    dn-events-extensions:event-message-string "FTP client login to remote host {remote-host} has been rejected, client appears blocked in client-list";
    dn-events-extensions:event-corrective-action-string "No corrective action.";
    dn-events-extensions:event-trigger-component-string "Management";
    dn-events-extensions:event-group "Management";
    leaf remote-host {
      type string;
      description
        "Remote host address, can be an IP address or as hostname";
    }
  }

  // NETCONF events

  notification NETCONF_SESSION_DISCONNECTED {
    description
      "The NETCONF session was remotely closed by the NETCONF client.";
    dn-events-extensions:event-severity-level "Notice";
    dn-events-extensions:event-message-string "NETCONF user {user-name} has closed the NETCONF session {session-id} from remote host {remote-host} VRF {vrf-name}";
    dn-events-extensions:event-corrective-action-string "No corrective action.";
    dn-events-extensions:event-trigger-component-string "Netconf";
    dn-events-extensions:event-group "Management";
    leaf user-name {
      type string;
      description
        "Client user-name";
    }
    leaf remote-host {
      type string;
      description
        "Remote host address, can be an IP address or as hostname";
    }
    leaf session-id {
      type uint16;
      description
        "Session ID";
    }
    leaf vrf-name {
      description
        "The VRF in which the event happened";
      type string;
    }
  }

  notification NETCONF_MAXIMUM_SESSIONS_LIMIT_REACHED {
    description
      "The maximum number of concurrent active NETCONF sessions was reached. The system cannot add new NETCONF sessions until one of active NETCONF sessions is closed.";
    dn-events-extensions:event-severity-level "Warning";
    dn-events-extensions:event-message-string "Number of NETCONF sessions has reached the configured maximum of {max-sessions}";
    dn-events-extensions:event-corrective-action-string
      "<p>Terminate active NETCONF sessions to the system:</p>
       <ol>
       <li>Run command 'show system netconf sessions' to view the existing NETCONF sessions.</li>
       <li>Select a session-id for the connection you want to terminate.</li>
       <li>Run the command 'clear netconf session [session-id]'.</li>
       </ol>";
    dn-events-extensions:event-trigger-component-string "Netconf";
    dn-events-extensions:event-group "Management";
    leaf max-sessions {
      type uint8;
      description
        "Maximum number of sessions";
    }
  }

  notification NETCONF_SESSION_LOGIN {
    description
      "The NETCONF client successfully connected to the NETCONF server.";
    dn-events-extensions:event-severity-level "Info";
    dn-events-extensions:event-message-string "NETCONF user {user-name} has logged in from remote host {remote-host} VRF {vrf-name}";
    dn-events-extensions:event-corrective-action-string "This is informational, no corrective action required.";
    dn-events-extensions:event-trigger-component-string "Netconf";
    dn-events-extensions:event-group "Management";
    leaf user-name {
      type string;
      description
        "System user-name";
    }
    leaf remote-host {
      type string;
      description
        "Remote host address, can be an IP address or as hostname";
    }
    leaf vrf-name {
      description
        "The VRF in which the event happened";
      type string;
    }
  }

  notification NETCONF_SESSION_LOGIN_FAILED {
    description
      "A new NETCONF session to the system was rejected due to incorrect credentials.";
    dn-events-extensions:event-severity-level "Notice";
    dn-events-extensions:event-message-string "NETCONF user {user-name} login attempt from remote host {remote-host} VRF {vrf-name} has been rejected due to incorrect credentials";
    dn-events-extensions:event-corrective-action-string "This is informational, no corrective action required.";
    dn-events-extensions:event-trigger-component-string "Netconf";
    dn-events-extensions:event-group "Management";
    leaf user-name {
      type string;
      description
        "System user-name";
    }
    leaf remote-host {
      type string;
      description
        "Remote host address, can be an IP address or as hostname";
    }
    leaf vrf-name {
      description
        "The VRF in which the event happened";
      type string;
    }
  }

  notification NETCONF_MAXIMUM_SESSIONS_LIMIT_CLEARED {
    description
      "The number of concurrent NETCONF sessions to the system has moved below the maximum number of connections.";
    dn-events-extensions:event-severity-level "Info";
    dn-events-extensions:event-message-string "Number of NETCONF sessions is below the configured maximum of {max-sessions}";
    dn-events-extensions:event-corrective-action-string "This is informational, no corrective action required.";
    dn-events-extensions:event-trigger-component-string "Netconf";
    dn-events-extensions:event-group "Management";
    leaf max-sessions {
      type uint8;
      description
        "Maximum number of sessions";
    }
  }

  notification NETCONF_SESSION_TERMINATED {
    description
      "The user has terminated the NETCONF session using the 'clear netconf session' command.";
    dn-events-extensions:event-severity-level "Notice";
    dn-events-extensions:event-message-string "User {user-name} has terminated the NETCONF session {session-id}";
    dn-events-extensions:event-corrective-action-string "This is informational, no corrective action required.";
    dn-events-extensions:event-trigger-component-string "Netconf";
    dn-events-extensions:event-group "Management";
    leaf user-name {
      type string;
      description
        "System user-name";
    }
    leaf session-id {
      type uint16;
      description
        "Session ID";
    }
  }

  notification NETCONF_CLIENT_LIST_CONFIG {
    description
      "The NETCONF client-list was configured/updated.";
    dn-events-extensions:event-severity-level "Info";
    dn-events-extensions:event-message-string "User {user-name} has changed NETCONF client-list configuration on VRF {vrf-name}";
    dn-events-extensions:event-corrective-action-string "This is informational, no corrective action required.";
    dn-events-extensions:event-trigger-component-string "Transaction-manager";
    dn-events-extensions:event-group "Management";
    leaf user-name {
      type string;
      description
        "System user-name";
    }
    leaf vrf-name {
      description
        "The VRF in which the event happened";
      type string;
    }
  }

  notification NETCONF_ADMIN_STATE_CONFIG {
    description
      "The user has changed the NETCONF server admin-state configuration.";
    dn-events-extensions:event-severity-level "Info";
    dn-events-extensions:event-message-string "User {user-name} has changed NETCONF admin-state configuration to {new-state} on VRF {vrf-name}";
    dn-events-extensions:event-corrective-action-string "This is informational, no corrective action required.";
    dn-events-extensions:event-trigger-component-string "Transaction-manager";
    dn-events-extensions:event-group "Management";
    leaf user-name {
      type string;
      description
        "System user-name";
    }
    leaf new-state {
      type string;
      description
        "New configured admin state";
    }
    leaf vrf-name {
      description
        "The VRF in which the event happened";
      type string;
    }
  }

  notification NETCONF_SESSION_TIMEOUT_CONFIG {
    description
      "The user changed the NETCONF session timeout parameter.";
    dn-events-extensions:event-severity-level "Info";
    dn-events-extensions:event-message-string "User {user-name} has changed NETCONF session timeout parameter";
    dn-events-extensions:event-corrective-action-string "This is informational, no corrective action required.";
    dn-events-extensions:event-trigger-component-string "Transaction-manager";
    dn-events-extensions:event-group "Management";
    leaf user-name {
      type string;
      description
        "System user-name";
    }
  }

  notification NETCONF_PORT_CONFIG {
    description
      "The user changed the NETCONF listening port.";
    dn-events-extensions:event-severity-level "Info";
    dn-events-extensions:event-message-string "User {user-name} has changed NETCONF server listening port to port {port}";
    dn-events-extensions:event-corrective-action-string "This is informational, no corrective action required.";
    dn-events-extensions:event-trigger-component-string "Transaction-manager";
    dn-events-extensions:event-group "Management";
    leaf user-name {
      type string;
      description
        "System user-name";
    }
    leaf port {
      type uint16;
      description
        "Netconf listening port";
    }
  }

  notification NETCONF_SESSION_TIMEOUT {
    description
      "The NETCONF session was terminated due to a session timeout.";
    dn-events-extensions:event-severity-level "Notice";
    dn-events-extensions:event-message-string "NETCONF session {session-id} from remote host {remote-host} VRF {vrf-name} was terminated due to timeout";
    dn-events-extensions:event-corrective-action-string "This is informational, no corrective action required.";
    dn-events-extensions:event-trigger-component-string "Netconf";
    dn-events-extensions:event-group "Management";
    leaf remote-host {
      type string;
      description
        "Remote host address, can be an IP address or as hostname";
    }
    leaf session-id {
      type uint16;
      description
        "Session ID";
    }
    leaf vrf-name {
      description
        "The VRF in which the event happened";
      type string;
    }
  }

  notification NETCONF_SESSION_LOGIN_DENIED {
    description
      "NETCONF has rejected a new session to the system due to a client-list configuration.";
    dn-events-extensions:event-severity-level "Notice";
    dn-events-extensions:event-message-string "NETCONF login attempt from remote host {remote-host} VRF {vrf-name} has been rejected due to client-list configuration";
    dn-events-extensions:event-corrective-action-string "This is informational, no corrective action required.";
    dn-events-extensions:event-trigger-component-string "Netconf";
    dn-events-extensions:event-group "Management";
    leaf remote-host {
      type string;
      description
        "Remote host address, can be an IP address or as hostname";
    }
    leaf vrf-name {
      description
        "The VRF in which the event happened";
      type string;
    }
  }

  notification NETCONF_MAXIMUM_SESSIONS_LIMIT_REJECT {
    description
      "A new NETCONF session to the system has been rejected since the number of concurrent active NETCONF sessions has reached the configured limit.";
    dn-events-extensions:event-severity-level "Notice";
    dn-events-extensions:event-message-string "A new NETCONF session of user {user-name} from remote host {remote-host} VRF {vrf-name} has been rejected since the number of concurrent active NETCONF sessions has reached the configured limit of {max-sessions}";
    dn-events-extensions:event-corrective-action-string "This is informational, no corrective action required.";
    dn-events-extensions:event-trigger-component-string "Netconf";
    dn-events-extensions:event-group "Management";
    leaf max-sessions {
      type uint8;
      description
        "Maximum number of sessions";
    }
    leaf user-name {
      type string;
      description
        "System user-name";
    }
    leaf remote-host {
      type string;
      description
        "Remote host address, can be an IP address or as hostname";
    }
    leaf vrf-name {
      description
        "The VRF in which the event happened";
      type string;
    }
  }

  notification NETCONF_SESSION_UNAUTHORIZED_USER_ROLE_REJECT {
    description
      "NETCONF has rejected a new session to the system due to unauthorized user role.";
    dn-events-extensions:event-severity-level "Notice";
    dn-events-extensions:event-message-string "NETCONF user {user-name} login attempt from remote host {remote-host} VRF {vrf-name} has been rejected due to unauthorized user role";
    dn-events-extensions:event-corrective-action-string "This is informational, no corrective action required.";
    dn-events-extensions:event-trigger-component-string "Netconf";
    dn-events-extensions:event-group "Management";
    leaf user-name {
      type string;
      description
        "System user-name";
    }
    leaf remote-host {
      type string;
      description
        "Remote host address, can be an IP address or as hostname";
    }
    leaf vrf-name {
      description
        "The VRF in which the event happened";
      type string;
    }
  }

  notification NETCONF_NACM_UNKNOWN_GROUP_REJECT {
    description
      "NETCONF has rejected a new session to the system due to group misconfiguration, group was received from AAA server but not configured on the device.";
    dn-events-extensions:event-severity-level "Notice";
    dn-events-extensions:event-message-string "NETCONF user {user-name} login attempt from remote host {remote-host} has been rejected due to unauthorized user group {group-name}";
    dn-events-extensions:event-corrective-action-string "This is informational, no corrective action required.";
    dn-events-extensions:event-trigger-component-string "Netconf";
    dn-events-extensions:event-group "Management";
    leaf user-name {
      type string;
      description
        "System user-name";
    }
    leaf remote-host {
      type string;
      description
        "Remote host address, can be an IP address or as hostname";
    }
    leaf group-name {
      type string;
      description
        "NACM group name";
    }
  }

  notification NETCONF_NACM_UNAUTHORIZED_OPERATION {
    description
      "NETCONF has rejected user action as user was unauthorized to perform requested operation.";
    dn-events-extensions:event-severity-level "Notice";
    dn-events-extensions:event-message-string "NETCONF user {user-name} from remote host {remote-host} action was rejected as the user is unauthorized to perform the requested operation {protocol-operation} on module {module-name}";
    dn-events-extensions:event-corrective-action-string "This is informational, no corrective action required.";
    dn-events-extensions:event-trigger-component-string "Netconf";
    dn-events-extensions:event-group "Management";
    leaf user-name {
      type string;
      description
        "System user-name";
    }
    leaf remote-host {
      type string;
      description
        "Remote host address, can be an IP address or as hostname";
    }
    leaf module-name {
      type string;
      description
        "The name of the yang module";
    }
    leaf protocol-operation {
      type string;
      description
        "User protocol operation";
    }
  }

  notification NETCONF_NACM_UNAUTHORIZED_DATA_ACCESS {
    description
      "NETCONF has rejected user action as user was unauthorized to access data node.";
    dn-events-extensions:event-severity-level "Notice";
    dn-events-extensions:event-message-string "NETCONF user {user-name} from remote host {remote-host} action was rejected as the user is unauthorized to access to path in module {module-name}";
    dn-events-extensions:event-corrective-action-string "This is informational, no corrective action required.";
    dn-events-extensions:event-trigger-component-string "Netconf";
    dn-events-extensions:event-group "Management";
    leaf user-name {
      type string;
      description
        "System user-name";
    }
    leaf remote-host {
      type string;
      description
        "Remote host address, can be an IP address or as hostname";
    }
    leaf module-name {
      type string;
      description
        "The name of the yang module";
    }
  }

  //GRPC events

  notification GRPC_MAXIMUM_SESSIONS_LIMIT_REACHED {
    description
      "The maximum number of concurrent active gRPC sessions was reached. The system cannot add new gRPC sessions until one of active gRPC sessions is closed.";
    dn-events-extensions:event-severity-level "Warning";
    dn-events-extensions:event-message-string "Number of gRPC sessions has reached the configured maximum ({max-number})";
    dn-events-extensions:event-corrective-action-string "No corrective action is required.";
    dn-events-extensions:event-trigger-component-string "WB";
    dn-events-extensions:event-group "Management";
    leaf max-number {
      type uint8;
      description
        "Maximum number of gRPC clients";
    }
  }

  notification GRPC_MAXIMUM_SESSIONS_LIMIT_CLEARED {
    description
      "The number of concurrent gRPC sessions to the system has moved below the maximum number of connections.";
    dn-events-extensions:event-severity-level "Info";
    dn-events-extensions:event-message-string "Number of gRPC sessions is below the configured maximum ({max-number})";
    dn-events-extensions:event-corrective-action-string "This is informational, no corrective action is required.";
    dn-events-extensions:event-trigger-component-string "WB";
    dn-events-extensions:event-group "Management";
    leaf max-number {
      type uint8;
      description
        "Maximum number of gRPC clients";
    }
  }

  notification GRPC_SESSION_LOGIN {
    description
      "A new gRPC user has logged in to subscribe to telemetry parameters.";
    dn-events-extensions:event-severity-level "Info";
    dn-events-extensions:event-message-string "gRPC user {user-name} has logged in from remote host {remote-host} on VRF {vrf-name}";
    dn-events-extensions:event-corrective-action-string "This is informational, no corrective action is required.";
    dn-events-extensions:event-trigger-component-string "WB";
    dn-events-extensions:event-group "Management";
    leaf user-name {
      type string;
      description
        "User-name that has logged in as a gRPC user";
    }
    leaf remote-host {
      type string;
      description
        "IP address of the remote host that has logged in as a gRPC user";
    }
    leaf vrf-name {
      type string;
      description
        "the vrf in which event happened";
    }
  }

  notification GRPC_SESSION_LOGIN_FAILED {
    description
      "A new gRPC session to the system was rejected due to incorrect credentials.";
    dn-events-extensions:event-severity-level "Notice";
    dn-events-extensions:event-message-string "gRPC user {user-name} login attempt from remote host {remote-host} on VRF {vrf-name} has been rejected due to incorrect credentials";
    dn-events-extensions:event-corrective-action-string "No corrective action is required.";
    dn-events-extensions:event-trigger-component-string "WB";
    dn-events-extensions:event-group "Management";
    leaf user-name {
      type string;
      description
        "User-name that has logged in as a gRPC user";
    }
    leaf remote-host {
      type string;
      description
        "IP address of the remote host that has logged in as a gRPC user";
    }
    leaf vrf-name {
      type string;
      description
        "the vrf in which event happened";
    }
  }

  notification GRPC_SESSION_DISCONNECTED {
    description
      "The gRPC session was remotely closed by the gRPC client.";
    dn-events-extensions:event-severity-level "Info";
    dn-events-extensions:event-message-string "gRPC user {user-name} has closed gRPC session {session-id} from remote host {remote-host} on VRF {vrf-name}";
    dn-events-extensions:event-corrective-action-string "This is informational, no corrective action is required.";
    dn-events-extensions:event-trigger-component-string "WB";
    dn-events-extensions:event-group "Management";
    leaf user-name {
      type string;
      description
        "User-name that has logged in as a gRPC user";
    }
    leaf remote-host {
      type string;
      description
        "IP address of the remote host that has logged in as a gRPC user";
    }
    leaf session-id {
      type uint16;
      description
        "gRPC session ID";
    }
    leaf vrf-name {
      type string;
      description
        "the vrf in which event happened";
    }
  }

  notification GRPC_SESSION_TERMINATED {
    description
      "The user has terminated the gRPC session using the 'clear grpc session' command.";
    dn-events-extensions:event-severity-level "Notice";
    dn-events-extensions:event-message-string "User {user-name} has terminated the gRPC session {session-id}";
    dn-events-extensions:event-corrective-action-string "No corrective action is required.";
    dn-events-extensions:event-trigger-component-string "WB";
    dn-events-extensions:event-group "Management";
    leaf user-name {
      type string;
      description
        "User-name that has logged in as a gRPC user";
    }
    leaf session-id {
      type uint16;
      description
        "gRPC session ID";
    }
  }

  notification GRPC_CLIENT_LIST_CONFIG {
    description
      "The gRPC client-list was configured/updated.";
    dn-events-extensions:event-severity-level "Info";
    dn-events-extensions:event-message-string "User {user-name} has changed gRPC client-list configuration";
    dn-events-extensions:event-corrective-action-string "This is informational, no corrective action is required.";
    dn-events-extensions:event-trigger-component-string "Transaction-manager";
    dn-events-extensions:event-group "Management";
    leaf user-name {
      type string;
      description
        "User-name that has logged in as a gRPC user";
    }
  }

  notification GRPC_ADMIN_STATE_CONFIG {
    description
      "The user has changed the gRPC VRF admin-state configuration.";
    dn-events-extensions:event-severity-level "Info";
    dn-events-extensions:event-message-string "User {user-name} has changed gRPC server configuration on VRF {vrf-name} to {new-state}";
    dn-events-extensions:event-corrective-action-string "This is informational, no corrective action is required.";
    dn-events-extensions:event-trigger-component-string "Transaction-manager";
    dn-events-extensions:event-group "Management";
    leaf user-name {
      type string;
      description
        "User-name that has logged in as a gRPC user";
    }
    leaf new-state {
      type string;
      description
        "gRPC server admin-state after the change";
    }
    leaf vrf-name {
      type string;
      description
        "the vrf in which event happened";
    }
  }

  notification GRPC_PORT_CONFIG {
    description
      "The user changed the GRPC listening port.";
    dn-events-extensions:event-severity-level "Info";
    dn-events-extensions:event-message-string "User {user-name} has changed GRPC server listening port to port {port}";
    dn-events-extensions:event-corrective-action-string "This is informational, no corrective action required.";
    dn-events-extensions:event-trigger-component-string "Transaction-manager";
    dn-events-extensions:event-group "Management";
    leaf user-name {
      type string;
      description
        "System user-name";
    }
    leaf port {
      type uint16;
      description
        "GRPC listening port";
    }
  }

  notification GRPC_SESSION_LOGIN_DENIED {
    description
      "gRPC has rejected a new session to the system due to the client-list configuration.";
    dn-events-extensions:event-severity-level "Notice";
    dn-events-extensions:event-message-string "gRPC login attempt from remote host {remote-host} on VRF {vrf-name} has been rejected due to client-list configuration;";
    dn-events-extensions:event-corrective-action-string "No corrective action is required.";
    dn-events-extensions:event-trigger-component-string "WB";
    dn-events-extensions:event-group "Management";
    leaf remote-host {
      type string;
      description
        "IP address of the remote host that has logged in as a gRPC user";
    }
    leaf vrf-name {
      type string;
      description
        "the vrf in which event happened";
    }
  }

  notification GRPC_SESSION_REJECTED_RESOURCE_EXHAUSTED {
    description
      "gRPC has rejected a new session to the system because the maximum exported rate per system has been crossed.";
    dn-events-extensions:event-severity-level "Notice";
    dn-events-extensions:event-message-string "gRPC login attempt from remote host {remote-host} on VRF {vrf-name} has been rejected, the maximum exported rate per system has been crossed;";
    dn-events-extensions:event-corrective-action-string "No corrective action is required.";
    dn-events-extensions:event-trigger-component-string "WB";
    dn-events-extensions:event-group "Management";
    leaf remote-host {
      type string;
      description
        "IP address of the remote host that has logged in as a gRPC user";
    }
    leaf vrf-name {
      type string;
      description
        "the vrf in which event happened";
    }
  }

  notification GRPC_SESSION_REJECTED_BAD_CERTIFICATE {
    description
      "gRPC has rejected a new session to the system because of missing or bad certificate.";
    dn-events-extensions:event-severity-level "Warning";
    dn-events-extensions:event-message-string "gRPC login attempt from remote host {remote-host} on VRF {vrf-name} has been rejected";
    dn-events-extensions:event-corrective-action-string "Check the gRPC configuration and installed certificates.";
    dn-events-extensions:event-trigger-component-string "WB";
    dn-events-extensions:event-group "Management";
    leaf remote-host {
      type string;
      description
        "IP address of the remote host that has logged in as a gRPC user";
    }
    leaf vrf-name {
      type string;
      description
        "the vrf in which event happened";
    }
  }

  notification GRPC_SESSION_PERMISSION_DENIED {
    description
      "gRPC has rejected a new session to the system due to an unauthorized user role.";
    dn-events-extensions:event-severity-level "Notice";
    dn-events-extensions:event-message-string "gRPC user {user-name} login attempt from remote host {remote-host} on VRF {vrf-name} has been rejected due to unauthorized user role";
    dn-events-extensions:event-corrective-action-string "No corrective action is required.";
    dn-events-extensions:event-trigger-component-string "WB";
    dn-events-extensions:event-group "Management";
    leaf user-name {
      type string;
      description
        "User-name that has logged in as a gRPC user";
    }
    leaf remote-host {
      type string;
      description
        "IP address of the remote host that has logged in as a gRPC user";
    }
    leaf vrf-name {
      type string;
      description
        "the vrf in which event happened";
    }
  }

  notification TELEMETRY_DIALOUT_SESSION_ESTABLISHED {
    description
      "The telemetry dialout session was established.";
    dn-events-extensions:event-severity-level "Notice";
    dn-events-extensions:event-message-string "Telemetry Dial-Out session to destination {ip-address}:{port} on VRF {vrf-name} in destination group {destination-group-id} that attached to subscription {subscription-id} was established";
    dn-events-extensions:event-corrective-action-string "No corrective action is required.";
    dn-events-extensions:event-trigger-component-string "WB";
    dn-events-extensions:event-group "Management";
    leaf subscription-id {
      type string;
      description
        "The subscription ID";
    }
    leaf destination-group-id {
      type string;
      description
        "The destination group ID";
    }
    leaf ip-address {
      type string;
      description
        "IP address of the destination server";
    }
    leaf port {
      type string;
      description
        "Port number of the destination server";
    }
    leaf vrf-name {
      description
        "the vrf in which event happened";
      type string;
    }
  }

  notification TELEMETRY_DIALOUT_SESSION_DISCONNECTED {
    description
      "The telemetry dialout session was disconnected.";
    dn-events-extensions:event-severity-level "Notice";
    dn-events-extensions:event-message-string "Telemetry Dial-Out session to destination {ip-address}:{port} on VRF {vrf-name} in destination group {destination-group-id} that attached to subscription {subscription-id} was disconnected";
    dn-events-extensions:event-corrective-action-string "No corrective action is required.";
    dn-events-extensions:event-trigger-component-string "WB";
    dn-events-extensions:event-group "Management";
    leaf subscription-id {
      type string;
      description
        "The subscription ID";
    }
    leaf destination-group-id {
      type string;
      description
        "The destination group ID";
    }
    leaf ip-address {
      type string;
      description
        "IP address of the destination server";
    }
    leaf port {
      type string;
      description
        "Port number of the destination server";
    }
    leaf vrf-name {
      description
        "the vrf in which event happened";
      type string;
    }
  }

  notification TELEMETRY_DIALOUT_SESSION_FAILED {
    description
      "The telemetry dialout session was disconnected or terminated.";
    dn-events-extensions:event-severity-level "Notice";
    dn-events-extensions:event-message-string "Telemetry Dial-Out connection to destination {ip-address}:{port} on VRF {vrf-name} in destination group {destination-group-id} that attached to subscription {subscription-id} could not connect due to {error-reason}";
    dn-events-extensions:event-corrective-action-string "No corrective action is required.";
    dn-events-extensions:event-trigger-component-string "WB";
    dn-events-extensions:event-group "Management";
    leaf subscription-id {
      type string;
      description
        "The subscription ID";
    }
    leaf destination-group-id {
      type string;
      description
        "The destination group ID";
    }
    leaf ip-address {
      type string;
      description
        "IP address of the destination server";
    }
    leaf port {
      type string;
      description
        "Port number of the destination server";
    }
    leaf vrf-name {
      description
        "the vrf in which event happened";
      type string;
    }
    leaf error-reason {
      type string;
      description
        "error reason - can be certificate error, unsupported algorithm, etc...";
    }
  }

  notification TELEMETRY_DIALOUT_GLOBAL_ADMIN_STATE_CONFIG {
    description
      "The user has changed the system wide telemetry dial-out feature admin-state configuration.";
    dn-events-extensions:event-severity-level "Info";
    dn-events-extensions:event-message-string "User {user-name} has changed system wide telemetry dial-out feature admin state to {new-state}";
    dn-events-extensions:event-corrective-action-string "This is informational, no corrective action is required.";
    dn-events-extensions:event-trigger-component-string "Transaction-manager";
    dn-events-extensions:event-group "Management";
    leaf user-name {
      type string;
      description
        "System user-name";
    }
    leaf new-state {
      type string;
      description
        "SNMP trap server admin-state after the change";
    }
  }

  notification TELEMETRY_DIALOUT_SUBSCRIPTION_ADMIN_STATE_CONFIG {
    description
      "The user has changed the Telemetry Dial-Out subscription admin-state configuration.";
    dn-events-extensions:event-severity-level "Info";
    dn-events-extensions:event-message-string "User {user-name} has changed Telemetry Dial-Out per subscription {subscription-id} admin state to {new-state}";
    dn-events-extensions:event-corrective-action-string "This is informational, no corrective action is required.";
    dn-events-extensions:event-trigger-component-string "Transaction-manager";
    dn-events-extensions:event-group "Management";
    leaf user-name {
      type string;
      description
        "System user-name";
    }
    leaf subscription-id {
      type string;
      description
        "The subscription ID";
    }
    leaf new-state {
      type string;
      description
        "SNMP trap server admin-state after the change";
    }
  }

  notification TELEMETRY_DIALOUT_SUBSCRIPTION_CONFIG {
    description
      "Subscription has been added, removed or updated. The update can be a change in a destination group or a sensor group attached to the subscription.";
    dn-events-extensions:event-severity-level "Info";
    dn-events-extensions:event-message-string "User {user-name} has {action} Subscription {subscription-id} configuration";
    dn-events-extensions:event-corrective-action-string "This is informational, no corrective action required.";
    dn-events-extensions:event-trigger-component-string "Transaction-manager";
    dn-events-extensions:event-group "Management";
    leaf user-name {
      type string;
      description
        "System user-name";
    }
    leaf action {
      type string;
      description
        "Server configuration action (added/removed/updated)";
    }
    leaf subscription-id {
      type string;
      description
        "Subscription ID that was added/removed/updated";
    }
  }

  notification GRPC_SECURITY_CIPHERS_CONFIG {
    description
      "The list of configured ciphers used by the grpc server";
    dn-events-extensions:event-severity-level "Notice";
    dn-events-extensions:event-message-string "The configured blacklist of TLS ciphers used by the grpc server was updated. Current list: {tls-ciphers-list}. (if empty, no ciphers are blacklisted)";
    dn-events-extensions:event-corrective-action-string "No corrective action.";
    dn-events-extensions:event-trigger-component-string "WB";
    dn-events-extensions:event-group "Management";
    leaf tls-ciphers-list {
      type string;
      description
        "the configured list of tls ciphers";
    }
  }

  // SNMP events

  notification SNMP_TRAP_SERVER_CONFIG {
    description
      "The SNMP trap server configuration has changed.";
    dn-events-extensions:event-severity-level "Info";
    dn-events-extensions:event-message-string "User {user-name} has {action} SNMP trap server {server-address} in VRF {vrf-name} configuration";
    dn-events-extensions:event-corrective-action-string "This is informational, no corrective action required.";
    dn-events-extensions:event-trigger-component-string "Transaction-manager";
    dn-events-extensions:event-group "Management";
    leaf user-name {
      type string;
      description
        "System user-name";
    }
    leaf action {
      type string;
      description
        "Server configuration action (added/removed)";
    }
    leaf server-address {
      type string;
      description
        "Server address, can be an IP address or as hostname";
    }
    leaf vrf-name {
      description
        "the vrf in which event happened";
      type string;
    }
  }

  notification SNMP_TRAP_SERVER_BUFFER_OVERFLOW_REACHED {
    description
      "SNMP trap server's buffer has reached the maximum value, new traps will be discarded";
    dn-events-extensions:event-severity-level "Info";
    dn-events-extensions:event-message-string "Snmp trap server {server-address} on VRF {vrf-name} buffer has overflowed";
    dn-events-extensions:event-corrective-action-string "This is informational, no corrective action required.";
    dn-events-extensions:event-trigger-component-string "Transaction-manager";
    dn-events-extensions:event-group "Management";
    leaf vrf-name {
      type string;
      description
        "The server vrf";
    }
    leaf server-address {
      type string;
      description
        "Server address, can be an IP address or as hostname";
    }
  }

  notification SNMP_TRAP_SERVER_BUFFER_OVERFLOW_CLEARED {
    description
      "The SNMP trap serve's buffer was cleared.";
    dn-events-extensions:event-severity-level "Info";
    dn-events-extensions:event-message-string "Snmp trap server {server-address} on VRF {vrf-name} buffer overflow has beed cleared";
    dn-events-extensions:event-corrective-action-string "This is informational, no corrective action required.";
    dn-events-extensions:event-trigger-component-string "Transaction-manager";
    dn-events-extensions:event-group "Management";
    leaf vrf-name {
      type string;
      description
        "The server vrf";
    }
    leaf server-address {
      type string;
      description
        "Server address, can be an IP address or as hostname";
    }
  }

  notification SNMP_CLIENT_LIST_CONFIG {
    description
      "The SNMP client list configuration has changed.";
    dn-events-extensions:event-severity-level "Info";
    dn-events-extensions:event-message-string "User {user-name} has changed the SNMP client list configuration in VRF {vrf-name}";
    dn-events-extensions:event-corrective-action-string "This is informational, no corrective action required.";
    dn-events-extensions:event-trigger-component-string "Transaction-manager";
    dn-events-extensions:event-group "Management";
    leaf user-name {
      type string;
      description
        "System user-name";
    }
    leaf vrf-name {
      description
        "the vrf in which event happened";
      type string;
    }
  }

  notification SNMP_AUTHENTICATION_FAILED {
    description
      "SNMP session failed due to incorrect community or user credentials.";
    dn-events-extensions:event-severity-level "Notice";
    dn-events-extensions:event-message-string "SNMP session from address {remote-address} in VRF {vrf-name} failed due to incorrect community or user credentials {credentials}.";
    dn-events-extensions:event-corrective-action-string "Make sure the credentials are configured the same way on both the local and remote system.";
    dn-events-extensions:event-trigger-component-string "Management";
    dn-events-extensions:event-group "Management";
    dn-events-extensions:event-snmp-trap-name "authenticationFailure";
    dn-events-extensions:event-snmp-trap-generic-type "authenticationFailure";
    dn-events-extensions:event-snmp-trap-oid ".1.3.6.1.6.3.1.1.5.5";
    leaf remote-address {
      type string;
      description
        "Remote network address";
    }
    leaf credentials {
      type string;
      description
        "User or community which failed";
    }
    leaf vrf-name {
      description
        "the vrf in which event happened";
      type string;
    }
  }

  notification SNMP_TRAP_SERVER_ADMIN_STATE_CONFIG {
    description
      "The user has changed the SNMP trap server admin-state configuration.";
    dn-events-extensions:event-severity-level "Info";
    dn-events-extensions:event-message-string "User {user-name} has changed SNMP trap server configuration in VRF {vrf-name} to {new-state}";
    dn-events-extensions:event-corrective-action-string "This is informational, no corrective action is required.";
    dn-events-extensions:event-trigger-component-string "Transaction-manager";
    dn-events-extensions:event-group "Management";
    leaf user-name {
      type string;
      description
        "System user-name";
    }
    leaf new-state {
      type string;
      description
        "SNMP trap server admin-state after the change";
    }
    leaf vrf-name {
      description
        "the vrf in which event happened";
      type string;
    }
  }

  notification SNMP_ADMIN_STATE_CONFIG {
    description
      "The user has changed the SNMP server admin-state configuration.";
    dn-events-extensions:event-severity-level "Info";
    dn-events-extensions:event-message-string "User {user-name} has changed SNMP server configuration in VRF {vrf-name} to {new-state}";
    dn-events-extensions:event-corrective-action-string "This is informational, no corrective action is required.";
    dn-events-extensions:event-trigger-component-string "Transaction-manager";
    dn-events-extensions:event-group "Management";
    leaf user-name {
      type string;
      description
        "System user-name";
    }
    leaf new-state {
      type string;
      description
        "SNMP server admin-state after the change";
    }
    leaf vrf-name {
      description
        "the vrf in which event happened";
      type string;
    }
  }

  notification SNMP_TRAP_SERVER_HOLD_DOWN_PERIOD_STARTED {
    description
      "The SNMP trap server did not acknowledge many InformRequests and Hold Down period has now begun.";
    dn-events-extensions:event-severity-level "Warning";
    dn-events-extensions:event-message-string "Snmp trap server {server-address} on VRF {vrf-name} is not responding to Inform messages";
    dn-events-extensions:event-corrective-action-string "Check the SNMP Trap Server status and configuration.";
    dn-events-extensions:event-trigger-component-string "Transaction-manager";
    dn-events-extensions:event-group "Management";
    leaf vrf-name {
      type string;
      description
        "The server vrf";
    }
    leaf server-address {
      type string;
      description
        "Server address, can be an IP address or as hostname";
    }
  }

  notification SNMP_TRAP_SERVER_HOLD_DOWN_PERIOD_ENDED {
    description
      "The Hold Down Period has ended,  InformRequests will be sent to the trap-server.";
    dn-events-extensions:event-severity-level "Info";
    dn-events-extensions:event-message-string "Snmp trap server {server-address} on VRF {vrf-name} Inform messages hold down period has ended, Inform messages will be sent to the server";
    dn-events-extensions:event-corrective-action-string "This is informational, no corrective action is required.";
    dn-events-extensions:event-trigger-component-string "Transaction-manager";
    dn-events-extensions:event-group "Management";
    leaf vrf-name {
      type string;
      description
        "The server vrf";
    }
    leaf server-address {
      type string;
      description
        "Server address, can be an IP address or as hostname";
    }
  }

  notification SNMP_TRAP_SERVER_NACK_ON_INFORM {
    description
      "The SNMP trap server sent an error in response to the InformRequest.";
    dn-events-extensions:event-severity-level "Warning";
    dn-events-extensions:event-message-string "Snmp trap server {server-address} on VRF {vrf-name} sent an error response {error-value} to the Inform with RequestId {request-id}";
    dn-events-extensions:event-corrective-action-string "Check the SNMP Trap Server status and configuration.";
    dn-events-extensions:event-trigger-component-string "Transaction-manager";
    dn-events-extensions:event-group "Management";
    leaf vrf-name {
      type string;
      description
        "The server vrf";
    }
    leaf server-address {
      type string;
      description
        "Server address, can be an IP address or as hostname";
    }
    leaf request-id {
      type uint32;
      description
        "Request-Id sent in the SNMP InformRequest-PDU";
    }
    leaf error-value {
      type string;
      description
        "Error response value";
    }
  }

  // TWAMP events

  notification TWAMP_ADMIN_STATE_CONFIG {
    description
      "The user has changed TWAMP admin-state configuration.";
    dn-events-extensions:event-severity-level "Info";
    dn-events-extensions:event-message-string "User {user-name} has changed TWAMP admin-state configuration to {new-state}";
    dn-events-extensions:event-corrective-action-string "This is informational, no corrective action required.";
    dn-events-extensions:event-trigger-component-string "Transaction-manager";
    dn-events-extensions:event-group "Services";
    leaf user-name {
      type string;
      description
        "System user-name";
    }
    leaf new-state {
      type string;
      description
        "TWAMP new admin state";
    }
  }

  notification TWAMP_SESSION_CONTROL_UP {
    description
      "The TWAMP control session is up.";
    dn-events-extensions:event-severity-level "Info";
    dn-events-extensions:event-message-string "TWAMP control connection ID {control-connection-id}. (remote address {remote-ip-address}:{remote-port}, local address {local-ip-address}:{local-port}, VRF {vrf-name})";
    dn-events-extensions:event-corrective-action-string "This is informational, no corrective action required.";
    dn-events-extensions:event-trigger-component-string "Twampd";
    dn-events-extensions:event-group "Services";
    leaf local-ip-address {
      type string;
      description
        "Local IP address";
    }
    leaf local-port {
      type uint16;
      description
        "Local port";
    }
    leaf remote-ip-address {
      type string;
      description
        "Remote IP address";
    }
    leaf remote-port {
      type uint16;
      description
        "Remote port";
    }
    leaf control-connection-id {
      type uint16;
      description
        "TWAMP Control connection ID";
    }
    leaf vrf-name {
      type string;
      description
        "The VRF in which the event has occured";
    }
  }

  notification TWAMP_SESSION_CONTROL_DOWN {
    description
      "The TWAMP control session is down.";
    dn-events-extensions:event-severity-level "Warning";
    dn-events-extensions:event-message-string "TWAMP control connection ID {control-connection-id} is down. (remote address {remote-ip-address}:{remote-port}, local address {local-ip-address}:{local-port}, VRF {vrf-name})";
    dn-events-extensions:event-corrective-action-string "No corrective action required.";
    dn-events-extensions:event-trigger-component-string "Twampd";
    dn-events-extensions:event-group "Services";
    leaf local-ip-address {
      type string;
      description
        "Local IP address";
    }
    leaf local-port {
      type uint16;
      description
        "Local port";
    }
    leaf remote-ip-address {
      type string;
      description
        "Remote IP address";
    }
    leaf remote-port {
      type uint16;
      description
        "Remote port";
    }
    leaf control-connection-id {
      type uint16;
      description
        "TWAMP Control connection ID";
    }
    leaf vrf-name {
      type string;
      description
        "The VRF in which the event has occured";
    }
  }

  notification TWAMP_SESSION_DATA_STATE_CHANGE {
    description
      "The TWAMP data session has changed its state.";
    dn-events-extensions:event-severity-level "Info";
    dn-events-extensions:event-message-string "TWAMP data session {data-session-id} under control connection ID {control-connection-id} state has changed from {old-state} to {new-state}. (remote address {remote-ip-address}:{remote-port}, local address {local-ip-address}:{local-port}, VRF {vrf-name})";
    dn-events-extensions:event-corrective-action-string "Contact Customer Support.";
    dn-events-extensions:event-trigger-component-string "Twampd";
    dn-events-extensions:event-group "Services";
    leaf old-state {
      type string;
      description
        "TWAMP data session old state";
    }
    leaf new-state {
      type string;
      description
        "TWAMP data session new state";
    }
    leaf local-ip-address {
      type string;
      description
        "Local IP address";
    }
    leaf local-port {
      type uint16;
      description
        "Local port";
    }
    leaf remote-ip-address {
      type string;
      description
        "Remote IP address";
    }
    leaf remote-port {
      type uint16;
      description
        "Remote port";
    }
    leaf control-connection-id {
      type uint16;
      description
        "TWAMP Control connection ID";
    }
    leaf data-session-id {
      type uint32;
      description
        "TWAMP Data session ID";
    }
    leaf vrf-name {
      type string;
      description
        "The VRF in which the event has occured";
    }
  }

  notification TWAMP_MAXIMUM_SESSIONS_CONTROL_LIMIT_REACHED {
    description
      "The number of concurrent TWAMP control sessions has reached the maximum number of sessions. No new TWAMP control sessions can be established.";
    dn-events-extensions:event-severity-level "Warning";
    dn-events-extensions:event-message-string "Number of TWAMP control sessions has reached the configured maximum ({max-twamp-control-sessions})";
    dn-events-extensions:event-corrective-action-string
      "<p>Terminate active TWAMP sessions to the system:</p>
       <ol>
       <li>Run command 'show services twamp sessions' to view the existing TWAMP sessions.</li>
       <li>Select a connection-id for the connection you want to terminate.</li>
       <li>Run the command 'clear twamp session [connection-id]'.</li>
       </ol>";
    dn-events-extensions:event-trigger-component-string "Twampd";
    dn-events-extensions:event-group "Services";
    leaf max-twamp-control-sessions {
      type uint8;
      description
        "Maximum number of TWAMP control sessions";
    }
  }

  notification TWAMP_MAXIMUM_SESSIONS_CONTROL_LIMIT_CLEARED {
    description
      "The TWAMP control session has cleared its limit, new control sessions are available.";
    dn-events-extensions:event-severity-level "Info";
    dn-events-extensions:event-message-string "Number of TWAMP control sessions is below the configured maximum ({max-twamp-control-sessions})";
    dn-events-extensions:event-corrective-action-string "This is informational, no corrective action required.";
    dn-events-extensions:event-trigger-component-string "Twampd";
    dn-events-extensions:event-group "Services";
    leaf max-twamp-control-sessions {
      type uint8;
      description
        "Maximum number of TWAMP control sessions";
    }
  }

  notification TWAMP_MAXIMUM_SESSIONS_DATA_LIMIT_REACHED {
    description
      "The number of concurrent TWAMP data sessions has reached the maximum number of sessions. No new TWAMP data sessions can be established.";
    dn-events-extensions:event-severity-level "Warning";
    dn-events-extensions:event-message-string "Number of TWAMP data sessions under control session ID {control-connection-id} has reached the configured maximum ({max-twamp-data-sessions})";
    dn-events-extensions:event-corrective-action-string
      "<p>Terminate active TWAMP sessions to the system:</p>
       <ol>
       <li>Run command 'show services twamp sessions' to view the existing TWAMP sessions.</li>
       <li>Select a connection-id for the connection you want to terminate.</li>
       <li>Run the command 'clear twamp session [connection-id]'.</li>
       </ol>";
    dn-events-extensions:event-trigger-component-string "Twampd";
    dn-events-extensions:event-group "Services";
    leaf max-twamp-data-sessions {
      type uint8;
      description
        "Maximum number of twamp data sessions";
    }
    leaf control-connection-id {
      type uint16;
      description
        "TWAMP Control connection ID";
    }
  }

  notification TWAMP_MAXIMUM_SESSIONS_DATA_LIMIT_CLEARED {
    description
      "The TWAMP control session has cleared its limit, new control sessions are available.";
    dn-events-extensions:event-severity-level "Info";
    dn-events-extensions:event-message-string "Number of TWAMP data sessions under control session ID {control-connection-id} is below the configured maximum ({max-twamp-data-sessions})";
    dn-events-extensions:event-corrective-action-string "This is informational, no corrective action required.";
    dn-events-extensions:event-trigger-component-string "Twampd";
    dn-events-extensions:event-group "Services";
    leaf max-twamp-data-sessions {
      type uint8;
      description
        "Maximum number of TWAMP data sessions";
    }
    leaf control-connection-id {
      type uint16;
      description
        "TWAMP Control connection ID";
    }
  }

  notification TWAMP_CLIENT_LOGIN_DENIED {
    description
      "TWAMP client access is denied due to incorrect credentials.";
    dn-events-extensions:event-severity-level "Warning";
    dn-events-extensions:event-message-string "TWAMP client login attempt from {remote-ip-address}:{remote-port} in VRF {vrf-name} was rejected due to client list configuration";
    dn-events-extensions:event-corrective-action-string "This is informational, no corrective action required.";
    dn-events-extensions:event-trigger-component-string "Twampd";
    dn-events-extensions:event-group "Services";
    leaf remote-ip-address {
      type string;
      description
        "Remote IP address";
    }
    leaf remote-port {
      type uint16;
      description
        "Remote port";
    }
    leaf vrf-name {
      type string;
      description
        "The VRF in which the event has occured";
    }
  }

  notification TWAMP_CLIENT_LIST_CONFIG {
    description
      "The user listed changed the TWAMP client list configuration.";
    dn-events-extensions:event-severity-level "Info";
    dn-events-extensions:event-message-string "User {user-name} changed the TWAMP client-list configuration for VRF {vrf-name}";
    dn-events-extensions:event-corrective-action-string "No corrective action.";
    dn-events-extensions:event-trigger-component-string "Transaction-manager";
    dn-events-extensions:event-group "Services";
    leaf user-name {
      type string;
      description
        "System user-name";
    }
    leaf vrf-name {
      type string;
      description
        "The VRF in which the event has occured";
    }
  }

  // Simple TWAMP events

  notification STAMP_TEST_FAILURE {
    description
      "The simple TWAMP test has failed due to threshold violation.";
    dn-events-extensions:event-severity-level "Notice";
    dn-events-extensions:event-message-string "Simple TWAMP session {session-name} from {source-address-and-port} to {destination-address-and-port} on VRF {vrf-name} has failed due to a violation of the configured {threshold-name} threshold of {threshold-value-and-units}.";
    dn-events-extensions:event-corrective-action-string "This is informational, no corrective action required.";
    dn-events-extensions:event-trigger-component-string "Stampd";
    dn-events-extensions:event-group "Services";
    leaf session-name {
      type string;
      description
        "Simple TWAMP session name";
    }
    leaf source-address-and-port {
      type string;
      description
        "The source IP address and port used for the Simple TWAMP monitoring session";
    }
    leaf destination-address-and-port {
      type string;
      description
        "The destination IP address and port used for the Simple TWAMP monitoring session";
    }
    leaf vrf-name {
      type string;
      description
        "The target VRF used for the Simple TWAMP monitoring session";
    }
    leaf threshold-name {
      type string;
      description
        "The name of the IP performance threshold that was violated";
    }
    leaf threshold-value-and-units {
      type string;
      description
        "The value (and units) that triggered the violation and caused the test to fail";
    }
  }

  notification STAMP_LINK_DELAY_ADVERTISEMENT {
    description
      "Link Delay advertisement was generated for the Simple TWAMP session.";
    dn-events-extensions:event-severity-level "Info";
    dn-events-extensions:event-message-string "Link delay advertisement has been generated for the Simple TWAMP session on interface {interface-name}. Reason: {reason}";
    dn-events-extensions:event-corrective-action-string "This is informational, no corrective action required.";
    dn-events-extensions:event-trigger-component-string "Stampd";
    dn-events-extensions:event-group "Services";
    leaf interface-name {
      type string;
      description
        "Interface name";
    }
    leaf reason {
      type string;
      description
        "The reason and that triggered the link delay advertisement";
    }
  }

  // ICMP Echo IP performance measurement events

  notification ICMP_ECHO_TEST_FAILURE {
    description
      "The ICMP echo IP performance measurement test has failed due to a threshold violation.";
    dn-events-extensions:event-severity-level "Notice";
    dn-events-extensions:event-message-string "ICMP echo IP performance measurement test session {session-name} (ID: {session-id}) from {source-address} to "
                                            + "{destination-address} in VRF {vrf-name} has failed due to a violation of the configured "
                                            + "{threshold-name} threshold of {threshold-value-and-units}. Recorded value: {calculated-violating-metric-and-units}";
    dn-events-extensions:event-corrective-action-string "This is informational, no corrective action required.";
    dn-events-extensions:event-trigger-component-string "NETPM";
    dn-events-extensions:event-group "NETPM";
    dn-events-extensions:event-snmp-trap-name "dnNetpmTestFailure";
    dn-events-extensions:event-snmp-trap-oid "1.3.6.1.4.1.49739.2.12.0.1";
    dn-events-extensions:event-snmp-trap-vars "dnSessionName.0 {session-name}; dnSourceAddress.0 {source-address}; dnDestinationAddress.0 {destination-address}; dnVrfName.0 {vrf-name}; dnThresholdName.0 {threshold-name}; dnThresholdValueAndUnits.0 {threshold-value-and-units}; dnCalculatedMetric.0 {calculated-violating-metric-and-units}";
    leaf session-name {
      type string;
      description
        "ICMP echo IP performance measurement test session name";
    }
    leaf session-id {
      type string;
      description
        "ICMP echo IP performance measurement test session id";
    }
    leaf source-address {
      type string;
      description
        "The source IP address used for the ICMP echo IP performance measurement test session";
    }
    leaf destination-address {
      type string;
      description
        "The destination IP address used for the ICMP echo IP performance measurement test session";
    }
    leaf vrf-name {
      type string;
      description
        "The target VRF used for the ICMP echo IP performance measurement test session";
    }
    leaf threshold-name {
      type string;
      description
        "The name of the IP performance metric threshold that was violated";
    }
    leaf threshold-value-and-units {
      type string;
      description
        "The configured threshold value (and units) that was breached";
    }
    leaf calculated-violating-metric-and-units {
      type string;
      description
        "The value (and units) that triggered the violation and caused the test to fail";
    }
  }

  // QoS events

  notification QOS_INTERNAL_ERROR {
    description
      "Internal Quality of Service error.";
    dn-events-extensions:event-severity-level "Error";
    dn-events-extensions:event-message-string "Quality of Service has encountered an error: {error-type}, {error-message}";
    dn-events-extensions:event-corrective-action-string "This is informational, no corrective action required.";
    dn-events-extensions:event-trigger-component-string "QOS";
    dn-events-extensions:event-group "QOS";
    leaf error-type {
      type string;
      description
        "Quality of Service error message type. i.e Hardware error";
    }
    leaf error-message {
      type string;
      description
        "Error description";
    }
  }

  notification QOS_RESOURCES_LIMIT_EXCEEDED {
    description
      "The number of Quality of Service resource configurations have reached the system limit, you cannot make any further commits.";
    dn-events-extensions:event-severity-level "Warning";
    dn-events-extensions:event-message-string "QoS resource configurations have reached system limit of {limit}. User {user-name} attempted to configure limited resource {resource-name} causing commit to fail";
    dn-events-extensions:event-corrective-action-string "Update QoS resource configuration to either increase the system limit or remove some resource configurations.";
    dn-events-extensions:event-trigger-component-string "QOS";
    dn-events-extensions:event-group "QOS";
    leaf limit {
      type string;
      description
        "Limit number";
    }
    leaf resource-name {
      type string;
      description
        "Quality of Service available hardware resource";
    }
    leaf user-name {
      type string;
      description
        "User name";
    }
  }

  notification QOS_PFC_DEADLOCK_FLAP_SUPPRESSION_THRESHOLD_EXCEEDED {
    description
      "PFC deadlock flap suppression threshold has been violated.";
    dn-events-extensions:event-severity-level "Warning";
    dn-events-extensions:event-message-string "The PFC deadlock flap suppression threshold was exceeded on interface {if-name} for traffic class {traffic-class} after {deadlock-occurrences} deadlock occurrences within {period} seconds.";
    dn-events-extensions:event-corrective-action-string "Check network configuration and reset PFC manually.";
    dn-events-extensions:event-trigger-component-string "QOS";
    dn-events-extensions:event-group "QOS";
    leaf if-name {
      type string;
      description
        "Interface name";
    }
    leaf traffic-class {
      type uint8 {
        range "0..7";
      }
      description
        "The applicable traffic class on the interface";
    }
    leaf deadlock-occurrences {
      type uint16 {
        range "1..500";
      }
      description
        "The number of deadlock occurrences on the interface within the sampling window";
    }
    leaf period {
      type uint16 {
        range "1..60";
      }
      description
        "The sampling window for PFC deadlock flap suppression";
      units "seconds";
    }
  }

  notification QOS_PFC_DEADLOCK_FLAP_SUPPRESSION_THRESHOLD_CLEARED {
    description
      "PFC deadlock flap suppression has moved below the configured threshold.";
    dn-events-extensions:event-severity-level "Info";
    dn-events-extensions:event-message-string "PFC deadlock flap suppression threshold cleared on interface {if-name} for traffic class {traffic-class}.";
    dn-events-extensions:event-corrective-action-string "No corrective action is required.";
    dn-events-extensions:event-trigger-component-string "QOS";
    dn-events-extensions:event-group "QOS";
    leaf if-name {
      type string;
      description
        "Interface name";
    }
    leaf traffic-class {
      type uint8 {
        range "0..7";
      }
      description
        "The applicable traffic class on the interface";
    }
  }

  // RIB events

  notification RIB_MAXIMUM_ROUTES_LIMIT_REACHED {
    description
      "The RIB has reached the maximum system limit of supported routes.";
    dn-events-extensions:event-severity-level "Warning";
    dn-events-extensions:event-message-string "RIB has reached the system limit of {limit} routes";
    dn-events-extensions:event-corrective-action-string "No corrective action.";
    dn-events-extensions:event-trigger-component-string "RIB";
    dn-events-extensions:event-group "RIB";
    leaf limit {
      type uint32;
      description
        "The accumulated IPv4 & IPv6 routes scale";
    }
  }

  notification RIB_MAXIMUM_ROUTES_LIMIT_CLEARED {
    description
      "The number of routes have moved below the system limit.";
    dn-events-extensions:event-severity-level "Info";
    dn-events-extensions:event-message-string "RIB is below the system limit of {limit} routes";
    dn-events-extensions:event-corrective-action-string "This is informational, no corrective action required.";
    dn-events-extensions:event-trigger-component-string "RIB";
    dn-events-extensions:event-group "RIB";
    leaf limit {
      type uint32;
      description
        "The accumulated IPv4 & IPv6 routes scale";
    }
  }

  notification RIB_MAXIMUM_ROUTES_THRESHOLD_EXCEEDED {
    description
      "RIB has crossed the system threshold for the number of supported routes.";
    dn-events-extensions:event-severity-level "Notice";
    dn-events-extensions:event-message-string "RIB crossed the system threshold {threshold}% of the limit ({limit}), the current number of routes are ({numeric-value})";
    dn-events-extensions:event-corrective-action-string "No corrective action.";
    dn-events-extensions:event-trigger-component-string "RIB";
    dn-events-extensions:event-group "RIB";
    leaf threshold {
      type uint8;
      description
        "Threshold percent";
    }
    leaf numeric-value {
      type uint32;
      description
        "Current number of routes in routing tables";
    }
    leaf limit {
      type uint32;
      description
        "The accumulated IPv4 & IPv6 routes scale";
    }
  }

  notification RIB_MAXIMUM_ROUTES_THRESHOLD_CLEARED {
    description
      "The RIB has moved below the threshold for the number of supported routes.";
    dn-events-extensions:event-severity-level "Info";
    dn-events-extensions:event-message-string "RIB is below the threshold {threshold}% of the limit ({limit}), the current number of routes are ({numeric-value})";
    dn-events-extensions:event-corrective-action-string "This is informational, no corrective action required.";
    dn-events-extensions:event-trigger-component-string "RIB";
    dn-events-extensions:event-group "RIB";
    leaf threshold {
      type uint8;
      description
        "Threshold percent";
    }
    leaf numeric-value {
      type uint32;
      description
        "Current number of routes in routing tables";
    }
    leaf limit {
      type uint32;
      description
        "The accumulated IPv4 & IPv6 routes scale";
    }
  }

  notification VRF_IPV4_MAXIMUM_ROUTES_LIMIT_REACHED {
    description
      "The RIB VRF has reached the maximum limit of supported ipv4 routes.";
    dn-events-extensions:event-severity-level "Warning";
    dn-events-extensions:event-message-string "RIB VRF instance {vrf-name} has reached the maximum-route limit of {limit} IPv4 routes";
    dn-events-extensions:event-corrective-action-string "Verify number of learned routes per routing protocols running in the VRF.";
    dn-events-extensions:event-trigger-component-string "RIB";
    dn-events-extensions:event-group "RIB";
    leaf vrf-name {
      description
        "the vrf in which event happened";
      type string;
    }
    leaf limit {
      type uint32;
      description
        "The accumulated IPv4 routes scale";
    }
  }

  notification VRF_IPV4_MAXIMUM_ROUTES_LIMIT_CLEARED {
    description
      "The number of routes have moved below the system limit.";
    dn-events-extensions:event-severity-level "Info";
    dn-events-extensions:event-message-string "RIB VRF instance {vrf-name} is below maximum-route limit of {limit} IPv4 routes";
    dn-events-extensions:event-corrective-action-string "This is informational, no corrective action required.";
    dn-events-extensions:event-trigger-component-string "RIB";
    dn-events-extensions:event-group "RIB";
    leaf vrf-name {
      description
        "the vrf in which event happened";
      type string;
    }
    leaf limit {
      type uint32;
      description
        "The accumulated IPv4 routes scale";
    }
  }

  notification VRF_IPV4_MAXIMUM_ROUTES_THRESHOLD_EXCEEDED {
    description
      "RIB has crossed the system threshold for the number of supported routes.";
    dn-events-extensions:event-severity-level "Notice";
    dn-events-extensions:event-message-string "RIB VRF instance {vrf-name} crossed the vrf threshold {threshold}% of the limit ({limit}) for IPv4 routes, the current number of IPv4 routes are ({numeric-value})";
    dn-events-extensions:event-corrective-action-string "Verify number of learned routes per routing protocols running in the VRF.";
    dn-events-extensions:event-trigger-component-string "RIB";
    dn-events-extensions:event-group "RIB";
    leaf vrf-name {
      description
        "the vrf in which event happened";
      type string;
    }
    leaf threshold {
      type uint8;
      description
        "Threshold percent";
    }
    leaf numeric-value {
      type uint32;
      description
        "Current number of routes in routing tables";
    }
    leaf limit {
      type uint32;
      description
        "The accumulated IPv4 routes scale";
    }
  }

  notification VRF_IPV4_MAXIMUM_ROUTES_THRESHOLD_CLEARED {
    description
      "The RIB has moved below the threshold for the number of supported routes.";
    dn-events-extensions:event-severity-level "Info";
    dn-events-extensions:event-message-string "RIB VRF instance {vrf-name} is below the threshold {threshold}% of the limit ({limit}) for IPv4 routes, the current number of IPv4 routes are ({numeric-value})";
    dn-events-extensions:event-corrective-action-string "This is informational, no corrective action required.";
    dn-events-extensions:event-trigger-component-string "RIB";
    dn-events-extensions:event-group "RIB";
    leaf vrf-name {
      description
        "the vrf in which event happened";
      type string;
    }
    leaf threshold {
      type uint8;
      description
        "Threshold percent";
    }
    leaf numeric-value {
      type uint32;
      description
        "Current number of routes in routing tables";
    }
    leaf limit {
      type uint32;
      description
        "The accumulated IPv4 routes scale";
    }
  }

  notification VRF_IPV6_MAXIMUM_ROUTES_LIMIT_REACHED {
    description
      "The RIB VRF has reached the maximum limit of supported ipv6 routes.";
    dn-events-extensions:event-severity-level "Warning";
    dn-events-extensions:event-message-string "RIB VRF instance {vrf-name} has reached the maximum-route limit of {limit} IPv6 routes";
    dn-events-extensions:event-corrective-action-string "Verify number of learned routes per routing protocols running in the VRF.";
    dn-events-extensions:event-trigger-component-string "RIB";
    dn-events-extensions:event-group "RIB";
    leaf vrf-name {
      description
        "the vrf in which event happened";
      type string;
    }
    leaf limit {
      type uint32;
      description
        "The accumulated IPv6 routes scale";
    }
  }

  notification VRF_IPV6_MAXIMUM_ROUTES_LIMIT_CLEARED {
    description
      "The number of routes have moved below the system limit.";
    dn-events-extensions:event-severity-level "Info";
    dn-events-extensions:event-message-string "RIB VRF instance {vrf-name} is below maximum-route limit of {limit} IPv6 routes";
    dn-events-extensions:event-corrective-action-string "This is informational, no corrective action required.";
    dn-events-extensions:event-trigger-component-string "RIB";
    dn-events-extensions:event-group "RIB";
    leaf vrf-name {
      description
        "the vrf in which event happened";
      type string;
    }
    leaf limit {
      type uint32;
      description
        "The accumulated IPv6 routes scale";
    }
  }

  notification VRF_IPV6_MAXIMUM_ROUTES_THRESHOLD_EXCEEDED {
    description
      "RIB has crossed the system threshold for the number of supported routes.";
    dn-events-extensions:event-severity-level "Notice";
    dn-events-extensions:event-message-string "RIB VRF instance {vrf-name} crossed the vrf threshold {threshold}% of the limit ({limit}) for IPv6 routes, the current number of IPv6 routes are ({numeric-value})";
    dn-events-extensions:event-corrective-action-string "Verify number of learned routes per routing protocols running in the VRF.";
    dn-events-extensions:event-trigger-component-string "RIB";
    dn-events-extensions:event-group "RIB";
    leaf vrf-name {
      description
        "the vrf in which event happened";
      type string;
    }
    leaf threshold {
      type uint8;
      description
        "Threshold percent";
    }
    leaf numeric-value {
      type uint32;
      description
        "Current number of routes in routing tables";
    }
    leaf limit {
      type uint32;
      description
        "The accumulated IPv6 routes scale";
    }
  }

  notification VRF_IPV6_MAXIMUM_ROUTES_THRESHOLD_CLEARED {
    description
      "The RIB has moved below the threshold for the number of supported routes.";
    dn-events-extensions:event-severity-level "Info";
    dn-events-extensions:event-message-string "RIB VRF instance {vrf-name} is below the threshold {threshold}% of the limit ({limit}) for IPv6 routes, the current number of IPv6 routes are ({numeric-value})";
    dn-events-extensions:event-corrective-action-string "This is informational, no corrective action required.";
    dn-events-extensions:event-trigger-component-string "RIB";
    dn-events-extensions:event-group "RIB";
    leaf vrf-name {
      description
        "the vrf in which event happened";
      type string;
    }
    leaf threshold {
      type uint8;
      description
        "Threshold percent";
    }
    leaf numeric-value {
      type uint32;
      description
        "Current number of routes in routing tables";
    }
    leaf limit {
      type uint32;
      description
        "The accumulated IPv6 routes scale";
    }
  }

  notification RIB_MANAGER_INTERNAL_ERROR {
    description
      "RIB manager has encountered an internal error.";
    dn-events-extensions:event-severity-level "Error";
    dn-events-extensions:event-message-string "RIB manager has encountered an error: {error-type}, {error-message}";
    dn-events-extensions:event-corrective-action-string "Copy the error message and contact Customer Support.";
    dn-events-extensions:event-trigger-component-string "RIB";
    dn-events-extensions:event-group "RIB";
    leaf error-type {
      type string;
      description
        "Error group type";
    }
    leaf error-message {
      type string;
      description
        "Error description";
    }
  }

  notification RIB_MULTICAST_INSTALL_ERRORS_DETECTED {
    description
      "RIB multicast resource installation failed.";
    dn-events-extensions:event-severity-level "Warning";
    dn-events-extensions:event-message-string "RIB failed to install {multicast-resource}. Reason: {reason}. VRF instance {vrf-name}";
    dn-events-extensions:event-corrective-action-string "Review the 'show multicast route failed' output and the PIM configuration in the network.";
    dn-events-extensions:event-trigger-component-string "RIB";
    dn-events-extensions:event-group "RIB";
    leaf multicast-resource {
      type string;
      description
        "Multicast resource";
    }
    leaf reason {
      type string;
      description
        "Reason for install failure";
    }
    leaf vrf-name {
      description
        "the vrf in which event happened";
      type string;
    }
  }

  notification RIB_MULTICAST_INSTALL_ERRORS_CLEARED {
    description
      "All existing RIB multicast resource installation failures cleared.";
    dn-events-extensions:event-severity-level "Warning";
    dn-events-extensions:event-message-string "All RIB multicast related install errors have been cleared. VRF instance {vrf-name}";
    dn-events-extensions:event-corrective-action-string "No corrective action is required.";
    dn-events-extensions:event-trigger-component-string "RIB";
    dn-events-extensions:event-group "RIB";
    leaf vrf-name {
      description
        "the vrf in which event happened";
      type string;
    }
  }

  // CPRL events

  notification CPRL_RATE_LIMIT_CROSSED {
    description
      "The rate of the specific control protocol reached the configured maximum. This can happen due to intentional flooding of control packets by a DDoS or network misconfiguration.";
    dn-events-extensions:event-severity-level "Warning";
    dn-events-extensions:event-message-string "Protocol {control-protocol} has reached the configured maximum rate-limit";
    dn-events-extensions:event-corrective-action-string "Check the network topology/configuration and possible control plane DDoS events.";
    dn-events-extensions:event-trigger-component-string "WB Agent";
    dn-events-extensions:event-group "System";
    leaf control-protocol {
      type string;
      description
        "Control protocol name (e.g. BGP, OSPF, SSH)";
    }
  }

  // LACP events

  notification LACP_INTERFACE_UP {
    description
      "The LACP adjacency is 'up' on the indicated interface.";
    dn-events-extensions:event-severity-level "Info";
    dn-events-extensions:event-message-string "LACP adjacency on interface {if-name} is up on parent interface {parent-if-name}";
    dn-events-extensions:event-corrective-action-string "No corrective action.";
    dn-events-extensions:event-trigger-component-string "WB Agent";
    dn-events-extensions:event-group "LACP";
    leaf if-name {
      type string;
      description
        "Interface name";
    }
    leaf parent-if-name {
      type string;
      description
        "Parent interface name";
    }
  }

  notification LACP_INTERFACE_DOWN {
    description
      "The LACP adjacency is 'down' due to an LACP timeout on the indicated interface.";
    dn-events-extensions:event-severity-level "Notice";
    dn-events-extensions:event-message-string "LACP adjacency on interface {if-name} is down on parent interface {parent-if-name}";
    dn-events-extensions:event-corrective-action-string "No corrective action.";
    dn-events-extensions:event-trigger-component-string "WB Agent";
    dn-events-extensions:event-group "LACP";
    leaf if-name {
      type string;
      description
        "Interface name";
    }
    leaf parent-if-name {
      type string;
      description
        "Parent interface name";
    }
  }

  notification LACP_INTERFACE_STATE_CHANGE {
    description
      "LACP on interface has changed its state.";
    dn-events-extensions:event-severity-level "Info";
    dn-events-extensions:event-message-string "LACP state machine on interface {if-name} has changed to {state} on parent interface {parent-if-name}";
    dn-events-extensions:event-corrective-action-string "No corrective action.";
    dn-events-extensions:event-trigger-component-string "WB Agent";
    dn-events-extensions:event-group "LACP";
    dn-events-extensions:event-snmp-trap-name "dnLacpInterfaceStateChange";
    dn-events-extensions:event-snmp-trap-oid "1.3.6.1.4.1.49739.2.16.0.1";
    dn-events-extensions:event-snmp-trap-vars "dnLacpInterfaceStateInterfaceName.{if-index} {if-name};  dnLacpInterfaceStateLagInterfaceName.{if-index} {parent-if-name}; dnLacpInterfaceStateLacpState.{if-index} {state}";
    leaf if-index {
      type uint32;
      description
        "SNMP Interface index";
    }
    leaf if-name {
      type string;
      description
        "Interface name";
    }
    leaf state {
      type string;
      description
        "Current LACP state";
    }
    leaf parent-if-name {
      type string;
      description
        "Parent interface name";
    }
  }

  // LLDP events

  notification LLDP_NEIGHBOR_STATE_CHANGE {
    description
      "The LLDP neighbor state has changed on the indicated interface.";
    dn-events-extensions:event-severity-level "Info";
    dn-events-extensions:event-message-string "Interface {if-name} LLDP neighbor state has change to {state}";
    dn-events-extensions:event-corrective-action-string "This is informational, no corrective action required.";
    dn-events-extensions:event-trigger-component-string "LLDP";
    dn-events-extensions:event-group "LLDP";
    leaf if-name {
      type string;
      description
        "Interface name";
    }
    leaf state {
      type string;
      description
        "Current LLDP neighbor state";
    }
  }

  // VRRP events

  notification VRRP_GROUP_STATE_CHANGE {
    description
      "The VRRP state has changed on the indicated interface and group.";
    dn-events-extensions:event-severity-level "Info";
    dn-events-extensions:event-message-string "VRRP state on interface {if-name} address-family {afi} VRID {vrid} has changed from {old-state} to {new-state}. Reason: {reason}";
    dn-events-extensions:event-corrective-action-string "This is informational, no corrective action required.";
    dn-events-extensions:event-trigger-component-string "VRRP";
    dn-events-extensions:event-group "VRRP";
    leaf if-name {
      type string;
      description
        "Interface name";
    }
    leaf afi {
      type string;
      description
        "VRRP afi type";
    }
    leaf vrid {
      type string;
      description
        "VRRP group identifier";
    }
    leaf old-state {
      type string;
      description
        "Old VRRP state";
    }
    leaf new-state {
      type string;
      description
        "Current VRRP state";
    }
    leaf reason {
      type string;
      description
        "VRRP state change reason";
    }
  }

  notification VRRP_GROUP_PRIORITY_CHANGE {
    description
      "The VRRP priority has changed on the indicated interface and group.";
    dn-events-extensions:event-severity-level "Info";
    dn-events-extensions:event-message-string "VRRP priority on interface {if-name} address-family {afi} VRID {vrid} has changed from {old-priority} to {new-priority}. Reason: {reason}";
    dn-events-extensions:event-corrective-action-string "This is informational, no corrective action required.";
    dn-events-extensions:event-trigger-component-string "VRRP";
    dn-events-extensions:event-group "VRRP";
    leaf if-name {
      type string;
      description
        "Interface name";
    }
    leaf afi {
      type string;
      description
        "VRRP afi type";
    }
    leaf vrid {
      type string;
      description
        "VRRP group identifier";
    }
    leaf old-priority {
      type string;
      description
        "Old VRRP priority";
    }
    leaf new-priority {
      type string;
      description
        "New VRRP priority";
    }
    leaf reason {
      type string;
      description
        "VRRP priority change reason";
    }
  }

  // Integrity report events

  notification INTEGRITY_REPORT_GENERATION_STARTED {
    description
      "Integrity report collection started";
    dn-events-extensions:event-severity-level "Info";
    dn-events-extensions:event-message-string "System started generating the integrity report requested by {user-name}";
    dn-events-extensions:event-corrective-action-string "This is informational, no corrective action required";
    dn-events-extensions:event-trigger-component-string "CLI";
    dn-events-extensions:event-group "System";
    leaf user-name {
      type string;
      description
        "System user-name";
    }
  }

  notification INTEGRITY_REPORT_GENERATION_DONE {
    description
      "Integrity report collection done";
    dn-events-extensions:event-severity-level "Info";
    dn-events-extensions:event-message-string "System finished generating the integrity report requested by {user-name}";
    dn-events-extensions:event-corrective-action-string "This is informational, no corrective action required";
    dn-events-extensions:event-trigger-component-string "CLI";
    dn-events-extensions:event-group "System";
    leaf user-name {
      type string;
      description
        "System user-name";
    }
  }

  notification INTEGRITY_REPORT_GENERATION_FAILED {
    description
      "Integrity report collection failed";
    dn-events-extensions:event-severity-level "Warning";
    dn-events-extensions:event-message-string "System failed generating the integrity report requested by {user-name}";
    dn-events-extensions:event-corrective-action-string "In case of failure try regenerating the integrity report or wait for the previous run to finish";
    dn-events-extensions:event-trigger-component-string "CLI";
    dn-events-extensions:event-group "System";
    leaf user-name {
      type string;
      description
        "System user-name";
    }
  }

  notification SYNCER_SPLIT_BRAIN_DETECTED {
    description
      "A split brain condition has been detected.";
    dn-events-extensions:event-severity-level "Warning";
    dn-events-extensions:event-message-string "Syncer split brain detected on nodes {nce-list} which are not connected to local node.";
    dn-events-extensions:event-corrective-action-string "Mitigation is in-progress, no corrective action required";
    dn-events-extensions:event-trigger-component-string "Operational-infra";
    dn-events-extensions:event-group "Syncer";
    leaf nce-list {
      type string;
      description
        "List of NCEs that are in split brain";
    }
  }

  notification SYNCER_SPLIT_BRAIN_MITIGATED {
    description
      "A split brain condition has been mitigated.";
    dn-events-extensions:event-severity-level "Info";
    dn-events-extensions:event-message-string "Syncer split brain mitigated for nodes {nce-list}";
    dn-events-extensions:event-corrective-action-string "This is informational, no corrective action required";
    dn-events-extensions:event-trigger-component-string "Operational-infra";
    dn-events-extensions:event-group "Syncer";
    leaf nce-list {
      type string;
      description
        "List of NCEs that were in split brain";
    }
  }

  notification SYNCER_SPLIT_BRAIN_MITIGATION_FAILED {
    description
      "Failed to mitigate the split brain condition.";
    dn-events-extensions:event-severity-level "Error";
    dn-events-extensions:event-message-string "Syncer split brain mitigation failed for nodes {nce-list}";
    dn-events-extensions:event-corrective-action-string "Manual warm restart of the disconnected nodes";
    dn-events-extensions:event-trigger-component-string "Operational-infra";
    dn-events-extensions:event-group "Syncer";
    leaf nce-list {
      type string;
      description
        "List of NCEs that are in split brain";
    }
  }

  notification TRANSACTION_REMOTE_COMMIT_FAILED {
    description
      "The synced transaction from remote node wasn't commited successfully.";
    dn-events-extensions:event-severity-level "Info";
    dn-events-extensions:event-message-string "Remote commit failed to be executed on node {node-type}, id {node-id}, commit originator is node {remote-node-type} id {remote-node-id}, reason: {reason}";
    dn-events-extensions:event-corrective-action-string "In case of failure, check for the originator configuration";
    dn-events-extensions:event-trigger-component-string "Operational-infra";
    dn-events-extensions:event-group "Syncer";
    leaf node-type {
      type string;
      description
        "Node type";
    }
    leaf node-id {
      type uint16;
      description
        "Node ID";
    }
    leaf remote-node-type {
      type string;
      description
        "The commit originator node type";
    }
    leaf remote-node-id {
      type uint16;
      description
        "The commit originator Node ID";
    }
    leaf reason {
      type string;
      description
        "The reason for the commit failure";
    }
  }

  notification TRANSACTION_REMOTE_COMMIT_SUCCEEDED {
    description
      "The synced transaction from remote node commited successfully.";
    dn-events-extensions:event-severity-level "Info";
    dn-events-extensions:event-message-string "Remote commit succeeded to be executed on node {node-type}, id {node-id}, commit originator is node {remote-node-type} id {remote-node-id}";
    dn-events-extensions:event-corrective-action-string "This is informational, no corrective action required";
    dn-events-extensions:event-trigger-component-string "Operational-infra";
    dn-events-extensions:event-group "Syncer";
    leaf node-type {
      type string;
      description
        "Node type";
    }
    leaf node-id {
      type uint16;
      description
        "Node ID";
    }
    leaf remote-node-type {
      type string;
      description
        "The commit originator node type";
    }
    leaf remote-node-id {
      type uint16;
      description
        "The commit originator Node ID";
    }
  }

  notification TRANSACTION_REMOTE_AGENT_FAILED {
    description
      "The synced transaction from remote node wasn't successfully applied by the agent.";
    dn-events-extensions:event-severity-level "Info";
    dn-events-extensions:event-message-string "Remote commit failed to be executed on node {node-type}, id {node-id}, by the following agent {agent-name}, reason: {reason}";
    dn-events-extensions:event-corrective-action-string "In case of failure, check for the agent logs";
    dn-events-extensions:event-trigger-component-string "Operational-infra";
    dn-events-extensions:event-group "Syncer";
    leaf node-type {
      type string;
      description
        "Node type";
    }
    leaf node-id {
      type uint16;
      description
        "Node ID";
    }
    leaf agent-name {
      type string;
      description
        "The the agent name that processing the remote transaction";
    }
    leaf reason {
      type string;
      description
        "The reason for the commit failure";
    }
  }

  notification TRANSACTION_REMOTE_DB_CONNECTION_FAILED {
    description
      "Remote transaction couldn't connect to DB";
    dn-events-extensions:event-severity-level "Info";
    dn-events-extensions:event-message-string "Remote transaction on node {node-type}, id {node-id}, couldn't establish connection to DB";
    dn-events-extensions:event-corrective-action-string "Remote transaction agents will be synced on a later stage once connection will be etablished";
    dn-events-extensions:event-trigger-component-string "Operational-infra";
    dn-events-extensions:event-group "Syncer";
    leaf node-type {
      type string;
      description
        "Node type";
    }
    leaf node-id {
      type uint16;
      description
        "Node ID";
    }
  }

  notification TRANSACTION_REMOTE_DB_CONNECTION_SUCCEEDED {
    description
      "Remote transaction connected to DB";
    dn-events-extensions:event-severity-level "Info";
    dn-events-extensions:event-message-string "Remote transaction on node {node-type}, id {node-id}, established connection to DB";
    dn-events-extensions:event-corrective-action-string "This is informational, no corrective action required";
    dn-events-extensions:event-trigger-component-string "Operational-infra";
    dn-events-extensions:event-group "Syncer";
    leaf node-type {
      type string;
      description
        "Node type";
    }
    leaf node-id {
      type uint16;
      description
        "Node ID";
    }
  }

  // Interfaces events

  notification IF_ADMIN_STATE_CONFIG {
    description
      "The user has changed the indicated interface admin-state.";
    dn-events-extensions:event-severity-level "Info";
    dn-events-extensions:event-message-string "User {user-name} has changed interface {if-name} state to {new-state}";
    dn-events-extensions:event-corrective-action-string "This is informational, no corrective action required.";
    dn-events-extensions:event-trigger-component-string "Transaction-manager";
    dn-events-extensions:event-group "Interfaces";
    leaf new-state {
      type string;
      description
        "Interface state";
    }
    leaf if-name {
      type string;
      description
        "Interface name";
    }
    leaf user-name {
      type string;
      description
        "System user-name";
    }
  }

  notification IF_LINK_STATE_CHANGE_DOWN {
    description
      "The link state on the interface has moved to a 'down' state. The link state changed due to a link failure.";
    dn-events-extensions:event-severity-level "Warning";
    dn-events-extensions:event-message-string "Interface {if-name} link state has changed to {new-state}. Down reason {down-reason}";
    dn-events-extensions:event-corrective-action-string
      "<p>If the link state change was expected, for example due to planned maintenance, no corrective action is required. If the link state changed unexpectedly:</p>
       <ol>
       <li>Check that the cable is properly connected at both ends.</li>
       <li>Check if the interface configuration on either side of the connection has changed. If it has changed, make sure that the interface is properly configured. See the CLI configuration guide.</li>
       <li>If the problem persists, contact Customer Support.</li>
       </ol>";
    dn-events-extensions:event-trigger-component-string "WB Agent";
    dn-events-extensions:event-group "Interfaces";
    dn-events-extensions:event-snmp-trap-name "linkDown";
    dn-events-extensions:event-snmp-trap-generic-type "linkDown";
    dn-events-extensions:event-snmp-trap-oid "1.3.6.1.6.3.1.1.5.3";
    dn-events-extensions:event-snmp-trap-vars "ifIndex.{if-index} {if-index} ; ifAdminStatus.{if-index} {if-admin-status} ; ifOperStatus.{if-index} {if-oper-status} ; ifName.{if-index} {if-name}";
    leaf new-state {
      type string;
      description
        "Interface state";
    }
    leaf if-name {
      type string;
      description
        "Interface name";
    }
    leaf if-index {
      type uint32;
      description
        "SNMP Interface index";
    }
    leaf if-admin-status {
      type uint32;
      description
        "SNMP Admin Status
         SYNTAX INTEGER up(1), down(2), testing(3)";
    }
    leaf if-oper-status {
      type uint32;
      description
        "SNMP Oper Status
         SYNTAX INTEGER up(1), down(2), testing(3)";
    }
    leaf down-reason {
      type string;
      description
        "Interface down cause reason";
    }
  }

  notification IF_LINK_STATE_CHANGE_UP {
    description
      "The link state on the interface has moved to an 'up' state.";
    dn-events-extensions:event-severity-level "Info";
    dn-events-extensions:event-message-string "Interface {if-name} link state has changed to {new-state}";
    dn-events-extensions:event-corrective-action-string "This is informational, no corrective action required.";
    dn-events-extensions:event-trigger-component-string "WB Agent";
    dn-events-extensions:event-group "Interfaces";
    dn-events-extensions:event-snmp-trap-name "linkUp";
    dn-events-extensions:event-snmp-trap-generic-type "linkUp";
    dn-events-extensions:event-snmp-trap-oid "1.3.6.1.6.3.1.1.5.4";
    dn-events-extensions:event-snmp-trap-vars "ifIndex.{if-index} {if-index} ; ifAdminStatus.{if-index} {if-admin-status} ; ifOperStatus.{if-index} {if-oper-status} ; ifName.{if-index} {if-name}";
    leaf new-state {
      type string;
      description
        "Interface state";
    }
    leaf if-name {
      type string;
      description
        "Interface name";
    }
    leaf if-index {
      type uint32;
      description
        "SNMP Interface index";
    }
    leaf if-admin-status {
      type uint32;
      description
        "SNMP Admin Status
         SYNTAX INTEGER up(1), down(2), testing(3)";
    }
    leaf if-oper-status {
      type uint32;
      description
        "SNMP Oper Status
         SYNTAX INTEGER up(1), down(2), testing(3)";
    }
  }

  notification IF_LINK_STATE_CHANGE_LANE_DOWN {
    description
      "The link state on the interface has changed. One or more lanes became inactive.";
    dn-events-extensions:event-severity-level "Notice";
    dn-events-extensions:event-message-string "Interface {if-name} link state changed from {old-state} to {new-state}. Lanes: {active-lane-id-list} are up";
    dn-events-extensions:event-corrective-action-string "Check that the cable is properly connected at both ends.";
    dn-events-extensions:event-trigger-component-string "WB Agent";
    dn-events-extensions:event-group "Interfaces";
    leaf if-name {
      type string;
      description
        "Interface name";
    }
    leaf new-state {
      type string;
      description
        "Current interface state";
    }
    leaf old-state {
      type string;
      description
        "Previous interface State";
    }
    leaf active-lane-id-list {
      type string;
      description
        "All lane IDs which their status is up";
    }
  }

  notification IF_LINK_STATE_CHANGE {
    description
      "The link state on the interface has changed. Inactive lane(s) are now active.";
    dn-events-extensions:event-severity-level "Info";
    dn-events-extensions:event-message-string "Interface {if-name} link state changed from {old-state} to {new-state}. Lanes: {active-lane-id-list} are up";
    dn-events-extensions:event-corrective-action-string "This is informational, no corrective action required.";
    dn-events-extensions:event-trigger-component-string "WB Agent";
    dn-events-extensions:event-group "Interfaces";
    leaf if-name {
      type string;
      description
        "Interface name";
    }
    leaf new-state {
      type string;
      description
        "Current interface state";
    }
    leaf old-state {
      type string;
      description
        "Previous interface State";
    }
    leaf active-lane-id-list {
      type string;
      description
        "All lane IDs which their status is up";
    }
  }

  notification IF_LINK_STATE_DELAY {
    description
      "The link state changed state. The notification of this link state change was delayed due to the configured carrier delay.";
    dn-events-extensions:event-severity-level "Info";
    dn-events-extensions:event-message-string "Link state on interface {if-name} changed from {old-state} to {new-state} was delayed by carrier-delay for {delay} ms";
    dn-events-extensions:event-corrective-action-string
      "<p>If the link state change was expected, for example due to planned maintenance, no corrective action is required. If the link state changed unexpectedly:</p>
       <ol>
       <li>Check that the cable and transceiver is properly inserted at both ends.</li>
       <li>Check if the interface configuration on either side of the connection has changed. If it has changed, make sure that the interface is properly configured. See show config interfaces in the CLI configuration guide.</li>
       <li>If the problem persists, contact Customer Support.</li>
       </ol>";
    dn-events-extensions:event-trigger-component-string "WB Agent";
    dn-events-extensions:event-group "Interfaces";
    leaf if-name {
      type string;
      description
        "Interface name";
    }
    leaf new-state {
      type string;
      description
        "Link state after change";
    }
    leaf old-state {
      type string;
      description
        "Link state before change";
    }
    leaf delay {
      type uint16;
      description
        "Delay value configured for carrier-delay at the interface";
    }
  }

  notification IF_LINK_STATE_SUPPRESSED {
    description
      "Any additional link state changes have been suppressed due to interface dampening.";
    dn-events-extensions:event-severity-level "Info";
    dn-events-extensions:event-message-string "Link state changes on interface {if-name} have been suppressed";
    dn-events-extensions:event-corrective-action-string "No corrective action is required.";
    dn-events-extensions:event-trigger-component-string "Interface Dampening";
    dn-events-extensions:event-group "Interfaces";
    leaf if-name {
      type string;
      description
        "Interface name";
    }
  }

  notification IF_LINK_STATE_SUPPRESS_ENDED {
    description
      "Link state change suppression has ended because either the interface dampening penalty decay is below the reuse threshold, the maximum suppression timer has expired, or the penalty was manually cleared.";
    dn-events-extensions:event-severity-level "Info";
    dn-events-extensions:event-message-string "Link state change suppression ended on interface {if-name} due to {suppression-end-reason}";
    dn-events-extensions:event-corrective-action-string "No corrective action is required.";
    dn-events-extensions:event-trigger-component-string "Interface Dampening";
    dn-events-extensions:event-group "Interfaces";
    leaf if-name {
      type string;
      description
        "Interface name";
    }
    leaf suppression-end-reason {
      type enumeration {
        enum penalty-decayed-below-reuse-threshold {
          value 0;
        }
        enum max-suppress-timer-expired {
          value 1;
        }
        enum penalty-cleared-manually {
          value 2;
        }
      }
      description
        "Interface link state suppress end reasons";
    }
  }

  notification IF_LINK_LOCAL_FAULT_DETECTED {
    description
      "Local fault detected on the interface Reconciliation Sublayer. The interface had stopped sending packets and Remote Fault Indication sent to the peer router.";
    dn-events-extensions:event-severity-level "Warning";
    dn-events-extensions:event-message-string "Local fault detected on interface {if-name}";
    dn-events-extensions:event-corrective-action-string "<p>No corrective action is required.</p>";
    dn-events-extensions:event-trigger-component-string "WB Agent";
    dn-events-extensions:event-group "Interfaces";
    leaf if-name {
      type string;
      description
        "Interface name";
    }
  }

  notification IF_LINK_REMOTE_FAULT_DETECTED {
    description
      "Remote fault detected on the interface Reconciliation Sublayer. The interface had stopped sending packets and IDLE Symbol is being sent to the peer router.";
    dn-events-extensions:event-severity-level "Warning";
    dn-events-extensions:event-message-string "Remote fault detected on interface {if-name}";
    dn-events-extensions:event-corrective-action-string "<p>No corrective action is required.</p>";
    dn-events-extensions:event-trigger-component-string "WB Agent";
    dn-events-extensions:event-group "Interfaces";
    leaf if-name {
      type string;
      description
        "Interface name";
    }
  }

  notification IF_LINK_LOCAL_FAULT_CLEARED {
    description
      "Local fault cleared on the interface Reconciliation Sublayer. Interface operational state may turn up unless Carrier delay or interface dampening delay the interface state change.";
    dn-events-extensions:event-severity-level "Info";
    dn-events-extensions:event-message-string "Local fault cleared on interface {if-name}";
    dn-events-extensions:event-corrective-action-string "<p>No corrective action is required.</p>";
    dn-events-extensions:event-trigger-component-string "WB Agent";
    dn-events-extensions:event-group "Interfaces";
    leaf if-name {
      type string;
      description
        "Interface name";
    }
  }

  notification IF_LINK_REMOTE_FAULT_CLEARED {
    description
      "Remote fault cleared on the interface Reconciliation Sublayer. Interface operational state may turn up unless Carrier delay or interface dampening delay the interface state change.";
    dn-events-extensions:event-severity-level "Info";
    dn-events-extensions:event-message-string "Remote fault cleared on interface {if-name}";
    dn-events-extensions:event-corrective-action-string "<p>No corrective action is required.</p>";
    dn-events-extensions:event-trigger-component-string "WB Agent";
    dn-events-extensions:event-group "Interfaces";
    leaf if-name {
      type string;
      description
        "Interface name";
    }
  }

  notification IF_LINK_BER_SIGNAL_DEGRADE_DETECTED {
    description
      "A signal degradation on the specified interface has been detected.";
    dn-events-extensions:event-severity-level "Warning";
    dn-events-extensions:event-message-string "Signal degradation has been detected on interface {if-name}. The configured signal degrade bit error rate threshold of {sd-ber-threshold} has been exceeded, current BER measurement on the interface is {current-ber}.";
    dn-events-extensions:event-corrective-action-string "<p>No corrective action is required.</p>";
    dn-events-extensions:event-trigger-component-string "WB Agent";
    dn-events-extensions:event-group "Interfaces";
    leaf if-name {
      type string;
      description
        "Interface name";
    }
    leaf sd-ber-threshold {
      type uint32;
      description
        "The configured signal degrade bit error rate threshold";
    }
    leaf current-ber {
      type uint32;
      description
        "The current bit error rate measured on the interface within the sampling window";
    }
  }

  notification IF_LINK_BER_SIGNAL_DEGRADE_CLEARED {
    description
      "The signal degredation alarm on the specified interface has been cleared.";
    dn-events-extensions:event-severity-level "Info";
    dn-events-extensions:event-message-string "The signal degrade threshold violation on interface {if-name} has been cleared. Current BER measurement on the interface is {current-ber}.";
    dn-events-extensions:event-corrective-action-string "<p>No corrective action is required.</p>";
    dn-events-extensions:event-trigger-component-string "WB Agent";
    dn-events-extensions:event-group "Interfaces";
    leaf if-name {
      type string;
      description
        "Interface name";
    }
    leaf current-ber {
      type uint32;
      description
        "The current bit error rate measured on the interface within the sampling window";
    }
  }

  notification IF_LINK_BER_SIGNAL_FAILURE_DETECTED {
    description
      "A signal failure on the specified interface has been detected.";
    dn-events-extensions:event-severity-level "Warning";
    dn-events-extensions:event-message-string "Signal failure has been detected on interface {if-name}. The configured signal failure bit error rate threshold of {sf-ber-threshold} has been exceeded, current BER measurement on the interface is {current-ber}.";
    dn-events-extensions:event-corrective-action-string "<p>No corrective action is required.</p>";
    dn-events-extensions:event-trigger-component-string "WB Agent";
    dn-events-extensions:event-group "Interfaces";
    leaf if-name {
      type string;
      description
        "Interface name";
    }
    leaf sf-ber-threshold {
      type uint32;
      description
        "The configured signal failure bit error rate threshold";
    }
    leaf current-ber {
      type uint32;
      description
        "The current bit error rate measured on the interface within the sampling window";
    }
  }

  notification IF_LINK_BER_SIGNAL_FAILURE_CLEARED {
    description
      "The signal failure alarm on the specified interface has been cleared.";
    dn-events-extensions:event-severity-level "Info";
    dn-events-extensions:event-message-string "The signal failure threshold violation on interface {if-name} has been cleared. Current BER measurement on the interface is {current-ber}.";
    dn-events-extensions:event-corrective-action-string "<p>No corrective action is required.</p>";
    dn-events-extensions:event-trigger-component-string "WB Agent";
    dn-events-extensions:event-group "Interfaces";
    leaf if-name {
      type string;
      description
        "Interface name";
    }
    leaf current-ber {
      type uint32;
      description
        "The current bit error rate measured on the interface within the sampling window";
    }
  }

  notification IF_LINK_STATE_CHANGE_MIN_LINKS_REACHED {
    description
      "The link state has moved to a 'down' state due to the configured min-links limit being reached.";
    dn-events-extensions:event-severity-level "Info";
    dn-events-extensions:event-message-string "Link state of interface {if-name} has changed to 'down' state due to min-links {min-links} limit being reached";
    dn-events-extensions:event-corrective-action-string "This is informational, no corrective action required.";
    dn-events-extensions:event-trigger-component-string "WB Agent";
    dn-events-extensions:event-group "Interfaces";
    leaf min-links {
      type uint16;
      description
        "Min links configuration threshold";
    }
    leaf if-name {
      type string;
      description
        "Interface name";
    }
  }

  notification IF_LINK_STATE_CHANGE_MIN_LINKS_CLEARED {
    description
      "The min-links threshold violation has been cleared.";
    dn-events-extensions:event-severity-level "Info";
    dn-events-extensions:event-message-string "The min-links {min-links} threshold violation of interface {if-name} has been cleared";
    dn-events-extensions:event-corrective-action-string "This is informational, no corrective action required.";
    dn-events-extensions:event-trigger-component-string "WB Agent";
    dn-events-extensions:event-group "Interfaces";
    leaf min-links {
      type uint16;
      description
        "Min links configuration threshold";
    }
    leaf if-name {
      type string;
      description
        "Interface name";
    }
  }

  notification IF_LINK_STATE_CHANGE_MIN_BANDWIDTH_REACHED {
    description
      "The link state has moved to a 'down' state due to the configured min-bandwidth limit being reached.";
    dn-events-extensions:event-severity-level "Info";
    dn-events-extensions:event-message-string "Link state of interface {if-name} has changed to 'down' state due to min-bandwidth {min-bw} limit being reached";
    dn-events-extensions:event-corrective-action-string "This is informational, no corrective action required.";
    dn-events-extensions:event-trigger-component-string "WB Agent";
    dn-events-extensions:event-group "Interfaces";
    leaf min-bw {
      type uint64;
      description
        "Min bandwidth configuration threshold";
    }
    leaf if-name {
      type string;
      description
        "Interface name";
    }
  }

  notification IF_LINK_STATE_CHANGE_MIN_BANDWIDTH_CLEARED {
    description
      "The min-bandwidth threshold violation has been cleared.";
    dn-events-extensions:event-severity-level "Info";
    dn-events-extensions:event-message-string "The min-bandwidth {min-bw} threshold violation of interface {if-name} has been cleared";
    dn-events-extensions:event-corrective-action-string "This is informational, no corrective action required.";
    dn-events-extensions:event-trigger-component-string "WB Agent";
    dn-events-extensions:event-group "Interfaces";
    leaf min-bw {
      type uint64;
      description
        "Min bandwidth configuration threshold";
    }
    leaf if-name {
      type string;
      description
        "Interface name";
    }
  }

  notification IF_BREAKOUT_MODE_STATE_CONFIG {
    description
      "The interface breakout mode configuration has changed.";
    dn-events-extensions:event-severity-level "Info";
    dn-events-extensions:event-message-string "User {user-name} changed interface {if-name} breakout mode configuration to {new-mode}";
    dn-events-extensions:event-corrective-action-string "This is informational, no corrective action required.";
    dn-events-extensions:event-trigger-component-string "WB Agent";
    dn-events-extensions:event-group "Interfaces";
    leaf user-name {
      type string;
      description
        "User name";
    }
    leaf if-name {
      type string;
      description
        "Interface name";
    }
    leaf new-mode {
      type enumeration {
        enum 10g-4x;
        enum 100g-4x;
        enum 200g-2x;
        enum 100g-2x;
        enum 400g-2x;
        enum 200g-4x;
        enum 100g-4x-sdr100;
        enum 400g-4x;
        enum 800g-2x;
        enum none;
      }
      description
        "Interface breakout new mode";
    }
  }

  notification IF_BREAKOUT_HW_LIMITATION_CONFIG {
    description
      "The interface breakout configuration not supported due to hardware limitation.";
    dn-events-extensions:event-severity-level "Error";
    dn-events-extensions:event-message-string "Due to hardware limitation, breakout mode of both interfaces {if-name-1} and {if-name-2} must be configured to either 10g-4x or none.";
    dn-events-extensions:event-corrective-action-string "Correct configuration.";
    dn-events-extensions:event-trigger-component-string "WB Agent";
    dn-events-extensions:event-group "Interfaces";
    leaf if-name-1 {
      type string;
      description
        "Interface name";
    }
    leaf if-name-2 {
      type string;
      description
        "Interface name";
    }
  }

  notification IF_MTU_PROFILES_LIMIT_REACHED {
    description
      "The maximum MTU profile configuration (100%) has been reached. No new MTU profiles can be established.";
    dn-events-extensions:event-severity-level "Warning";
    dn-events-extensions:event-message-string "Number of current MTU profiles has reached the configured limit ({max-mtu-profiles})";
    dn-events-extensions:event-corrective-action-string
      "<p>Update the MTU configuration:</p>
       <ol>
       <li>Run command 'show interfaces' to view the existing MTU configurations.</li>
       <li>Update interface MTU configuration to be similar as other interfaces.</li>
       </ol>";
    dn-events-extensions:event-trigger-component-string "WB Agent";
    dn-events-extensions:event-group "Interfaces";
    leaf max-mtu-profiles {
      type uint8;
      description
        "Maximum MTU profiles per system";
    }
  }

  notification IF_MTU_PROFILES_LIMIT_CLEARED {
    description
      "The number of MTU profiles has moved below the maximum MTU profile configuration limit.";
    dn-events-extensions:event-severity-level "Info";
    dn-events-extensions:event-message-string "Number of MTU profiles is below the maximum MTU profile limit: ({max-mtu-profiles})";
    dn-events-extensions:event-corrective-action-string "This is informational, no corrective action required.";
    dn-events-extensions:event-trigger-component-string "WB Agent";
    dn-events-extensions:event-group "Interfaces";
    leaf max-mtu-profiles {
      type uint8;
      description
        "Maximum MTU profiles per system";
    }
  }

  notification IF_VLAN_EDITING_INGRESS_PROFILES_LIMIT_REACHED {
    description
      "The maximum ingress VLAN editing profiles configuration has been reached. No new ingress VLAN editing profiles can be added in the system.";
    dn-events-extensions:event-severity-level "Warning";
    dn-events-extensions:event-message-string "Number of current ingress VLAN editing profiles has reached its limit of {max-vlan-editing-ingress-profiles} profiles";
    dn-events-extensions:event-corrective-action-string
      "<p>Update the VLAN manipulation configuration:</p>
       <ol>
       <li>Run command 'show system npu-resources' to view the existing VLAN editing profiles.</li>
       <li>Update interface VLAN manipulation configuration to be similar to that of other interfaces to free profiles.</li>
       </ol>";
    dn-events-extensions:event-trigger-component-string "WB Agent";
    dn-events-extensions:event-group "Interfaces";
    leaf max-vlan-editing-ingress-profiles {
      type uint8;
      description
        "Maximum ingerss VLAN editing profiles per system";
    }
  }

  notification IF_VLAN_EDITING_INGRESS_PROFILES_LIMIT_CLEARED {
    description
      "The number of ingress VLAN editing profiles has moved below the maximum ingress VLAN editing profiles configuration limit.";
    dn-events-extensions:event-severity-level "Info";
    dn-events-extensions:event-message-string "Number of ingress VLAN editing profiles has moved below the maximum limit of {max-vlan-editing-ingress-profiles} profiles";
    dn-events-extensions:event-corrective-action-string "This is informational, no corrective action required.";
    dn-events-extensions:event-trigger-component-string "WB Agent";
    dn-events-extensions:event-group "Interfaces";
    leaf max-vlan-editing-ingress-profiles {
      type uint8;
      description
        "Maximum ingress VLAN editing profiles per system";
    }
  }

  notification IF_VLAN_EDITING_EGRESS_PROFILES_LIMIT_REACHED {
    description
      "The maximum egress VLAN editing profiles configuration has been reached. No new egress VLAN editing profiles can be added in the system.";
    dn-events-extensions:event-severity-level "Warning";
    dn-events-extensions:event-message-string "Number of current egress VLAN editing profiles has reached its limit of {max-vlan-editing-egress-profiles} profiles";
    dn-events-extensions:event-corrective-action-string
      "<p>Update the VLAN manipulation configuration:</p>
       <ol>
       <li>Run command 'show system npu-resources' to view the existing VLAN editing profiles.</li>
       <li>Update interface VLAN manipulation configuration to be similar to that of other interfaces to free profiles.</li>
       </ol>";
    dn-events-extensions:event-trigger-component-string "WB Agent";
    dn-events-extensions:event-group "Interfaces";
    leaf max-vlan-editing-egress-profiles {
      type uint8;
      description
        "Maximum egress VLAN editing profiles per system";
    }
  }

  notification IF_VLAN_EDITING_EGRESS_PROFILES_LIMIT_CLEARED {
    description
      "The number of egress VLAN editing profiles has moved below the maximum egress VLAN editing profiles configuration limit.";
    dn-events-extensions:event-severity-level "Info";
    dn-events-extensions:event-message-string "Number of egress VLAN editing profiles has moved below the maximum limit of {max-vlan-editing-egress-profiles} profiles";
    dn-events-extensions:event-corrective-action-string "This is informational, no corrective action required.";
    dn-events-extensions:event-trigger-component-string "WB Agent";
    dn-events-extensions:event-group "Interfaces";
    leaf max-vlan-editing-egress-profiles {
      type uint8;
      description
        "Maximum egress VLAN editing profiles per system";
    }
  }

  notification IF_BUNDLE_MEMBER_ADDED_CONFIG {
    description
      "A new member was added to the bundle interface.";
    dn-events-extensions:event-severity-level "Info";
    dn-events-extensions:event-message-string "Member {member-name} was added to the bundle interface {bundle-name}.";
    dn-events-extensions:event-corrective-action-string "This is informational, no corrective action required.";
    dn-events-extensions:event-trigger-component-string "WB Agent";
    dn-events-extensions:event-group "Interfaces";
    leaf member-name {
      type string;
      description
        "Interface name of the member that was added to the bundle";
    }
    leaf bundle-name {
      type string;
      description
        "Interface name of the bundle that member was added to";
    }
  }

  notification IF_BUNDLE_MEMBER_REMOVED_CONFIG {
    description
      "A member was removed from the bundle interface.";
    dn-events-extensions:event-severity-level "Info";
    dn-events-extensions:event-message-string "Member {member-name} was removed from the bundle interface {bundle-name}.";
    dn-events-extensions:event-corrective-action-string "This is informational, no corrective action required.";
    dn-events-extensions:event-trigger-component-string "WB Agent";
    dn-events-extensions:event-group "Interfaces";
    leaf member-name {
      type string;
      description
        "Interface name of the member that was removed from the bundle";
    }
    leaf bundle-name {
      type string;
      description
        "Interface name of the bundle that member was removed from";
    }
  }

  notification IF_CONTROL_TRAFFIC_DROP {
    description
      "A traffic drop was observed on one of the inner cluster control links. This may happen due to an internal error, cluster connectivity problems, or if a non-DNOS device is connected to the cluster management network.";
    dn-events-extensions:event-severity-level "Warning";
    dn-events-extensions:event-message-string "DNOS traffic drop on control interface {if-name}";
    dn-events-extensions:event-corrective-action-string "Check the control connectivity on the device.";
    dn-events-extensions:event-trigger-component-string "Cluster Manager";
    dn-events-extensions:event-group "Interfaces";
    leaf if-name {
      type string;
      description
        "Interface name";
    }
  }

  notification IF_DUPLICATE_IPV6_ADDRESS_DETECTED {
    description
      "A duplicate IPv6 unicast address was detected on the listed interface.";
    dn-events-extensions:event-severity-level "Warning";
    dn-events-extensions:event-message-string "Duplicate IPv6 unicast address {ipv6-unicast-address} on interface {if-name} was detected";
    dn-events-extensions:event-corrective-action-string "Check the IPv6 address configuration of the interface.";
    dn-events-extensions:event-trigger-component-string "WB Agent";
    dn-events-extensions:event-group "Interfaces";
    leaf if-name {
      type string;
      description
        "Interface name";
    }
    leaf ipv6-unicast-address {
      type string;
      description
        "IPv6 unicast address of the interface";
    }
  }

  notification IF_LINK_SPEED_RX_THRESHOLD_EXCEEDED {
    description
      "The interface link rx speed has crossed the threshold.";
    dn-events-extensions:event-severity-level "Warning";
    dn-events-extensions:event-message-string "Link rx speed of interface {if-name} is above utilization threshold ({threshold}%), current rx utilization rate is: {interface-input-utilization}% of max interface speed {interface-speed}Gbps";
    dn-events-extensions:event-corrective-action-string "No corrective action required.";
    dn-events-extensions:event-trigger-component-string "WB Agent";
    dn-events-extensions:event-group "Interfaces";
    dn-events-extensions:event-snmp-trap-name "dnRsIfLinkRxThresholdExceeded";
    dn-events-extensions:event-snmp-trap-oid ".1.3.6.1.4.1.49739.2.8.0.5";
    dn-events-extensions:event-snmp-trap-vars "dnRsIfLinkUtilThreshold.{if-index} {threshold} ; dnRsIfLinkInputUtilization.{if-index} {interface-input-utilization}";
    leaf if-name {
      type string;
      description
        "Interface name";
    }
    leaf if-index {
      type uint32;
      description
        "SNMP Interface index";
    }
    leaf threshold {
      type uint16;
      description
        "Threshold in percent";
    }
    leaf interface-input-utilization {
      type uint8;
      units "percent";
      description
        "Interface input utilization rate in percent";
    }
    leaf interface-speed {
      type uint32;
      description
        "Physical interface max bandwidth";
    }
  }

  notification IF_LINK_SPEED_TX_THRESHOLD_EXCEEDED {
    description
      "The interface link tx speed has crossed the threshold.";
    dn-events-extensions:event-severity-level "Warning";
    dn-events-extensions:event-message-string "Link tx speed of interface {if-name} is above utilization threshold ({threshold}%), current tx utilization rate is: {interface-output-utilization}% of max interface speed {interface-speed}Gbps";
    dn-events-extensions:event-corrective-action-string "No corrective action required.";
    dn-events-extensions:event-trigger-component-string "WB Agent";
    dn-events-extensions:event-group "Interfaces";
    dn-events-extensions:event-snmp-trap-name "dnRsIfLinkTxThresholdExceeded";
    dn-events-extensions:event-snmp-trap-oid ".1.3.6.1.4.1.49739.2.8.0.6";
    dn-events-extensions:event-snmp-trap-vars "dnRsIfLinkUtilThreshold.{if-index} {threshold} ; dnRsIfLinkOutputUtilization.{if-index} {interface-output-utilization}";
    leaf if-name {
      type string;
      description
        "Interface name";
    }
    leaf if-index {
      type uint32;
      description
        "SNMP Interface index";
    }
    leaf threshold {
      type uint16;
      description
        "Threshold in percent";
    }
    leaf interface-output-utilization {
      type uint8;
      units "percent";
      description
        "Interface output utilization rate in percent";
    }
    leaf interface-speed {
      type uint32;
      description
        "Physical interface max bandwidth";
    }
  }

  notification IF_LINK_SPEED_RX_THRESHOLD_CLEARED {
    description
      "The interface link rx speed is below crossed the threshold.";
    dn-events-extensions:event-severity-level "Info";
    dn-events-extensions:event-message-string "Link rx speed of interface {if-name} is below the threshold ({threshold}%), current rx utilization rate is: {interface-input-utilization}% of max interface speed {interface-speed}Gbps";
    dn-events-extensions:event-corrective-action-string "No corrective action required.";
    dn-events-extensions:event-trigger-component-string "WB Agent";
    dn-events-extensions:event-group "Interfaces";
    dn-events-extensions:event-snmp-trap-name "dnRsIfLinkRxThresholdCleared";
    dn-events-extensions:event-snmp-trap-oid ".1.3.6.1.4.1.49739.2.8.0.7";
    dn-events-extensions:event-snmp-trap-vars "dnRsIfLinkUtilThreshold.{if-index} {threshold} ; dnRsIfLinkInputUtilization.{if-index} {interface-input-utilization}";
    leaf if-name {
      type string;
      description
        "Interface name";
    }
    leaf if-index {
      type uint32;
      description
        "SNMP Interface index";
    }
    leaf threshold {
      type uint16;
      description
        "Threshold in percent";
    }
    leaf interface-input-utilization {
      type uint8;
      units "percent";
      description
        "Interface input utilization rate in percent";
    }
    leaf interface-speed {
      type uint32;
      description
        "Physical interface max bandwidth";
    }
  }

  notification IF_LINK_SPEED_TX_THRESHOLD_CLEARED {
    description
      "The interface link tx speed is below crossed the threshold.";
    dn-events-extensions:event-severity-level "Info";
    dn-events-extensions:event-message-string "Link tx speed of interface {if-name} is below the threshold ({threshold}%), current tx utilization rate is: {interface-output-utilization}% of max interface speed {interface-speed}Gbps";
    dn-events-extensions:event-corrective-action-string "No corrective action required.";
    dn-events-extensions:event-trigger-component-string "WB Agent";
    dn-events-extensions:event-group "Interfaces";
    dn-events-extensions:event-snmp-trap-name "dnRsIfLinkTxThresholdCleared";
    dn-events-extensions:event-snmp-trap-oid ".1.3.6.1.4.1.49739.2.8.0.8";
    dn-events-extensions:event-snmp-trap-vars "dnRsIfLinkUtilThreshold.{if-index} {threshold} ; dnRsIfLinkOutputUtilization.{if-index} {interface-output-utilization}";
    leaf if-name {
      type string;
      description
        "Interface name";
    }
    leaf if-index {
      type uint32;
      description
        "SNMP Interface index";
    }
    leaf threshold {
      type uint16;
      description
        "Threshold in percent";
    }
    leaf interface-output-utilization {
      type uint8;
      units "percent";
      description
        "Interface output utilization rate in percent";
    }
    leaf interface-speed {
      type uint32;
      description
        "Physical interface max bandwidth";
    }
  }

  // Hardware events

  notification PLATFORM_TRANSCEIVER_REMOVED {
    description
      "The transceiver of the indicated interface was removed. The link is unavailable.";
    dn-events-extensions:event-severity-level "Warning";
    dn-events-extensions:event-message-string "Interface {if-name} transceiver was removed";
    dn-events-extensions:event-corrective-action-string "No corrective action.";
    dn-events-extensions:event-trigger-component-string "WB Agent";
    dn-events-extensions:event-group "Platform";
    dn-events-extensions:event-snmp-trap-name "dnFruRemoved";
    dn-events-extensions:event-snmp-trap-oid ".1.3.6.1.4.1.49739.2.6.0.1";
    dn-events-extensions:event-snmp-trap-vars "entPhysicalContainedIn.CONVERTIDX(transcvIAddr,{if-name}) CONVERTIDX(transcvIAddrCont,{if-name})";
    leaf if-name {
      type string;
      description
        "Interface name";
    }
  }

  notification PLATFORM_TRANSCEIVER_INSERTED {
    description
      "The transceiver of the indicated interface was inserted. The link can be available.";
    dn-events-extensions:event-severity-level "Info";
    dn-events-extensions:event-message-string "Interface {if-name} transceiver was inserted";
    dn-events-extensions:event-corrective-action-string "No corrective action.";
    dn-events-extensions:event-trigger-component-string "WB Agent";
    dn-events-extensions:event-group "Platform";
    dn-events-extensions:event-snmp-trap-name "dnFruInserted";
    dn-events-extensions:event-snmp-trap-oid ".1.3.6.1.4.1.49739.2.6.0.2";
    dn-events-extensions:event-snmp-trap-vars "entPhysicalContainedIn.CONVERTIDX(transcvIAddr,{if-name}) CONVERTIDX(transcvIAddrCont,{if-name})";
    leaf if-name {
      type string;
      description
        "Interface name";
    }
  }

  notification PLATFORM_TRANSCEIVER_THERMAL_THRESHOLD_EXCEEDED {
    description
      "The temperature of the indicated transceiver interface exceeded the critical threshold.";
    dn-events-extensions:event-severity-level "Warning";
    dn-events-extensions:event-message-string "Interface {if-name} transceiver temperature exceeded critical {threshold} degC threshold.";
    dn-events-extensions:event-corrective-action-string "Check the temperature of the node's environment and consider replacing the transceiver.";
    dn-events-extensions:event-trigger-component-string "WB Agent";
    dn-events-extensions:event-group "Platform";
    leaf if-name {
      type string;
      description
        "Interface name";
    }
    leaf threshold {
      type uint16;
      description
        "Threshold temperature in Celsius degrees";
    }
  }

  notification PLATFORM_TRANSCEIVER_THERMAL_THRESHOLD_CLEARED {
    description
      "The temperature of the indicated transceiver interface is below the critical threshold.";
    dn-events-extensions:event-severity-level "Info";
    dn-events-extensions:event-message-string "Interface {if-name} transceiver temperature is below critical {threshold} degC threshold.";
    dn-events-extensions:event-corrective-action-string "No corrective action.";
    dn-events-extensions:event-trigger-component-string "WB Agent";
    dn-events-extensions:event-group "Platform";
    leaf if-name {
      type string;
      description
        "Interface name";
    }
    leaf threshold {
      type uint16;
      description
        "Threshold temperature in Celsius degrees";
    }
  }

  notification PLATFORM_TRANSCEIVER_RX_HIGH_WARNING {
    description
      "The transceiver input power of the indicated interface is too high and at a warning level.";
    dn-events-extensions:event-severity-level "Warning";
    dn-events-extensions:event-message-string "Interface {if-name} transceiver channel ID {channel-id} input power is above thershold {receive-power-alarm-high} dBm. Current RX power is {current-rx-power} dBm";
    dn-events-extensions:event-corrective-action-string "Check the fiber or transceivers on both sides.";
    dn-events-extensions:event-trigger-component-string "WB Agent";
    dn-events-extensions:event-group "Platform";
    dn-events-extensions:event-snmp-trap-name "dnHwMonTransceiverRxPowerHigh";
    dn-events-extensions:event-snmp-trap-oid ".1.3.6.1.4.1.49739.2.7.0.11";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerHighWarningThreshold.CONVERTIDX(transcvIAddr,{if-name}) {receive-power-warning-high};
       dnHwMonTransceiverRxPowerHighAlarmThreshold.CONVERTIDX(transcvIAddr,{if-name}) {receive-power-alarm-high}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-high {
      type int32;
      description
        "Transceiver's input power warning high thershold in dBm";
    }
    leaf receive-power-alarm-high {
      type int32;
      description
        "Transceiver's input power alarm high thershold in dBm";
    }
  }

  notification PLATFORM_TRANSCEIVER_RX_HIGH_WARNING_CLEAR {
    description
      "The transceiver high input power warning of the indicated interface is cleared.";
    dn-events-extensions:event-severity-level "Info";
    dn-events-extensions:event-message-string "Interface {if-name} transceiver channel ID {channel-id} high input power warning is cleared. Current RX power is {current-rx-power}";
    dn-events-extensions:event-corrective-action-string "No corrective action.";
    dn-events-extensions:event-trigger-component-string "WB Agent";
    dn-events-extensions:event-group "Platform";
    dn-events-extensions:event-snmp-trap-name "dnHwMonTransceiverRxPowerHighClear";
    dn-events-extensions:event-snmp-trap-oid ".1.3.6.1.4.1.49739.2.7.0.13";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerHighWarningThreshold.CONVERTIDX(transcvIAddr,{if-name}) {receive-power-warning-high};
       dnHwMonTransceiverRxPowerHighAlarmThreshold.CONVERTIDX(transcvIAddr,{if-name}) {receive-power-alarm-high}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-high {
      type int32;
      description
        "Transceiver's input power warning high thershold in dBm";
    }
    leaf receive-power-alarm-high {
      type int32;
      description
        "Transceiver's input power alarm high thershold in dBm";
    }
  }

  notification PLATFORM_TRANSCEIVER_TX_HIGH_WARNING {
    description
      "The transceiver output power of the indicated interface is too high and at a warning level.";
    dn-events-extensions:event-severity-level "Warning";
    dn-events-extensions:event-message-string "Interface {if-name} transceiver channel ID {channel-id} output power is above threshold {transmit-power-alarm-high} dBm. Current TX power is {current-tx-power} dBm";
    dn-events-extensions:event-corrective-action-string "Check the fiber or transceivers on both sides.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-high {
      type int32;
      description
        "Transceiver's output power warning high thershold in dBm";
    }
    leaf transmit-power-alarm-high {
      type int32;
      description
        "Transceiver's output power alarm high thershold in dBm";
    }
  }

  notification PLATFORM_TRANSCEIVER_TX_HIGH_WARNING_CLEAR {
    description
      "The transceiver high output power warning of the indicated interface is cleared.";
    dn-events-extensions:event-severity-level "Info";
    dn-events-extensions:event-message-string "Interface {if-name} transceiver channel ID {channel-id} high output power warning is cleared. Current TX power is {current-tx-power}";
    dn-events-extensions:event-corrective-action-string "No corrective action.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-high {
      type int32;
      description
        "Transceiver's output power warning high thershold in dBm";
    }
    leaf transmit-power-alarm-high {
      type int32;
      description
        "Transceiver's output power alarm high thershold in dBm";
    }
  }

  notification PLATFORM_TRANSCEIVER_RX_HIGH_ALARM {
    description
      "The transceiver input power of the indicated interface is too high and at alarm level.";
    dn-events-extensions:event-severity-level "Warning";
    dn-events-extensions:event-message-string "Interface {if-name} transceiver channel ID {channel-id} input power is above threshold {receive-power-alarm-high} dBm. Current RX power is {current-rx-power} dBm";
    dn-events-extensions:event-corrective-action-string "Check the fiber or transceivers on both sides.";
    dn-events-extensions:event-trigger-component-string "WB Agent";
    dn-events-extensions:event-group "Platform";
    dn-events-extensions:event-snmp-trap-name "dnHwMonTransceiverRxPowerHigh";
    dn-events-extensions:event-snmp-trap-oid ".1.3.6.1.4.1.49739.2.7.0.11";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerHighWarningThreshold.CONVERTIDX(transcvIAddr,{if-name}) {receive-power-warning-high};
       dnHwMonTransceiverRxPowerHighAlarmThreshold.CONVERTIDX(transcvIAddr,{if-name}) {receive-power-alarm-high}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-high {
      type int32;
      description
        "Transceiver's input power warning high thershold in dBm";
    }
    leaf receive-power-alarm-high {
      type int32;
      description
        "Transceiver's input power alarm high thershold in dBm";
    }
  }

  notification PLATFORM_TRANSCEIVER_RX_HIGH_ALARM_CLEAR {
    description
      "The transceiver high input power alarm of the indicated interface is cleared.";
    dn-events-extensions:event-severity-level "Info";
    dn-events-extensions:event-message-string "Interface {if-name} transceiver channel ID {channel-id} high input power alarm is cleared. Current RX power is {current-rx-power}";
    dn-events-extensions:event-corrective-action-string "No corrective action.";
    dn-events-extensions:event-trigger-component-string "WB Agent";
    dn-events-extensions:event-group "Platform";
    dn-events-extensions:event-snmp-trap-name "dnHwMonTransceiverRxPowerHighClear";
    dn-events-extensions:event-snmp-trap-oid ".1.3.6.1.4.1.49739.2.7.0.13";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerHighWarningThreshold.CONVERTIDX(transcvIAddr,{if-name}) {receive-power-warning-high};
       dnHwMonTransceiverRxPowerHighAlarmThreshold.CONVERTIDX(transcvIAddr,{if-name}) {receive-power-alarm-high}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-high {
      type int32;
      description
        "Transceiver's input power warning high thershold in dBm";
    }
    leaf receive-power-alarm-high {
      type int32;
      description
        "Transceiver's input power alarm high thershold in dBm";
    }
  }

  notification PLATFORM_TRANSCEIVER_TX_HIGH_ALARM {
    description
      "The transceiver output power of the indicated interface is too high and at alarm level.";
    dn-events-extensions:event-severity-level "Warning";
    dn-events-extensions:event-message-string "Interface {if-name} transceiver channel ID {channel-id} output power is above threshold {transmit-power-alarm-high} dBm. Current TX power is {current-tx-power} dBm";
    dn-events-extensions:event-corrective-action-string "Check the fiber or transceivers on both sides.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-high {
      type int32;
      description
        "Transceiver's output power warning high thershold in dBm";
    }
    leaf transmit-power-alarm-high {
      type int32;
      description
        "Transceiver's output power alarm high thershold in dBm";
    }
  }

  notification PLATFORM_TRANSCEIVER_TX_HIGH_ALARM_CLEAR {
    description
      "The transceiver high output power alarm of the indicated interface is cleared.";
    dn-events-extensions:event-severity-level "Info";
    dn-events-extensions:event-message-string "Interface {if-name} transceiver channel ID {channel-id} high output power alarm is cleared. Current TX power is {current-tx-power}";
    dn-events-extensions:event-corrective-action-string "No corrective action.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-high {
      type int32;
      description
        "Transceiver's output power warning high thershold in dBm";
    }
    leaf transmit-power-alarm-high {
      type int32;
      description
        "Transceiver's output power alarm high thershold in dBm";
    }
  }

  notification PLATFORM_TRANSCEIVER_RX_LOW_WARNING {
    description
      "The transceiver input of the indicated interface is too low and at a warning level.";
    dn-events-extensions:event-severity-level "Warning";
    dn-events-extensions:event-message-string "Interface {if-name} transceiver channel ID {channel-id} input power is below threshold {receive-power-alarm-low} dBm. Current RX power is {current-rx-power} dBm";
    dn-events-extensions:event-corrective-action-string "Check the fiber or transceivers on both sides.";
    dn-events-extensions:event-trigger-component-string "WB Agent";
    dn-events-extensions:event-group "Platform";
    dn-events-extensions:event-snmp-trap-name "dnHwMonTransceiverRxPowerLow";
    dn-events-extensions:event-snmp-trap-oid ".1.3.6.1.4.1.49739.2.7.0.12";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerLowWarningThreshold.CONVERTIDX(transcvIAddr,{if-name}) {receive-power-warning-low};
       dnHwMonTransceiverRxPowerLowAlarmThreshold.CONVERTIDX(transcvIAddr,{if-name}) {receive-power-alarm-low}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-low {
      type int32;
      description
        "Transceiver's input power warning low thershold in dBm";
    }
    leaf receive-power-alarm-low {
      type int32;
      description
        "Transceiver's input power alarm low thershold in dBm";
    }
  }

  notification PLATFORM_TRANSCEIVER_RX_LOW_WARNING_CLEAR {
    description
      "The transceiver low input power warning of the indicated interface is cleared.";
    dn-events-extensions:event-severity-level "Info";
    dn-events-extensions:event-message-string "Interface {if-name} transceiver channel ID {channel-id} low input power warning is cleared. Current RX power is {current-rx-power}";
    dn-events-extensions:event-corrective-action-string "No corrective action.";
    dn-events-extensions:event-trigger-component-string "WB Agent";
    dn-events-extensions:event-group "Platform";
    dn-events-extensions:event-snmp-trap-name "dnHwMonTransceiverRxPowerLowClear";
    dn-events-extensions:event-snmp-trap-oid ".1.3.6.1.4.1.49739.2.7.0.14";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerLowWarningThreshold.CONVERTIDX(transcvIAddr,{if-name}) {receive-power-warning-low};
       dnHwMonTransceiverRxPowerLowAlarmThreshold.CONVERTIDX(transcvIAddr,{if-name}) {receive-power-alarm-low}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-low {
      type int32;
      description
        "Transceiver's input power warning low thershold in dBm";
    }
    leaf receive-power-alarm-low {
      type int32;
      description
        "Transceiver's input power alarm low thershold in dBm";
    }
  }

  notification PLATFORM_TRANSCEIVER_TX_LOW_WARNING {
    description
      "The transceiver output of the indicated interface is too low and at a warning level.";
    dn-events-extensions:event-severity-level "Warning";
    dn-events-extensions:event-message-string "Interface {if-name} transceiver channel ID {channel-id} output power is below threshold {transmit-power-alarm-low} dBm. Current TX power is {current-tx-power} dBm";
    dn-events-extensions:event-corrective-action-string "Check the fiber or transceivers on both sides.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-low {
      type int32;
      description
        "Transceiver's output power warning low thershold in dBm";
    }
    leaf transmit-power-alarm-low {
      type int32;
      description
        "Transceiver's output power alarm low thershold in dBm";
    }
  }

  notification PLATFORM_TRANSCEIVER_TX_LOW_WARNING_CLEAR {
    description
      "The transceiver low output power warning of the indicated interface is cleared.";
    dn-events-extensions:event-severity-level "Info";
    dn-events-extensions:event-message-string "Interface {if-name} transceiver channel ID {channel-id} low output power warning is cleared. Current TX power is {current-tx-power}";
    dn-events-extensions:event-corrective-action-string "No corrective action.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-low {
      type int32;
      description
        "Transceiver's output power warning low thershold in dBm";
    }
    leaf transmit-power-alarm-low {
      type int32;
      description
        "Transceiver's output power alarm low thershold in dBm";
    }
  }

  notification PLATFORM_TRANSCEIVER_RX_LOW_ALARM {
    description
      "The transceiver input of the indicated interface is too low and at alarm level.";
    dn-events-extensions:event-severity-level "Warning";
    dn-events-extensions:event-message-string "Interface {if-name} transceiver channel ID {channel-id} input power is below threshold {receive-power-alarm-low} dBm. Current RX power is {current-rx-power} dBm";
    dn-events-extensions:event-corrective-action-string "Check the fiber or transceivers on both sides.";
    dn-events-extensions:event-trigger-component-string "WB Agent";
    dn-events-extensions:event-group "Platform";
    dn-events-extensions:event-snmp-trap-name "dnHwMonTransceiverRxPowerLow";
    dn-events-extensions:event-snmp-trap-oid ".1.3.6.1.4.1.49739.2.7.0.12";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerLowWarningThreshold.CONVERTIDX(transcvIAddr,{if-name}) {receive-power-warning-low};
       dnHwMonTransceiverRxPowerLowAlarmThreshold.CONVERTIDX(transcvIAddr,{if-name}) {receive-power-alarm-low}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-low {
      type int32;
      description
        "Transceiver's input power warning low thershold in dBm";
    }
    leaf receive-power-alarm-low {
      type int32;
      description
        "Transceiver's input power alarm low thershold in dBm";
    }
  }

  notification PLATFORM_TRANSCEIVER_RX_LOW_ALARM_CLEAR {
    description
      "The transceiver low input power alarm of the indicated interface is cleared.";
    dn-events-extensions:event-severity-level "Info";
    dn-events-extensions:event-message-string "Interface {if-name} transceiver channel ID {channel-id} low input power alarm is cleared. Current RX power is {current-rx-power}";
    dn-events-extensions:event-corrective-action-string "No corrective action.";
    dn-events-extensions:event-trigger-component-string "WB Agent";
    dn-events-extensions:event-group "Platform";
    dn-events-extensions:event-snmp-trap-name "dnHwMonTransceiverRxPowerLowClear";
    dn-events-extensions:event-snmp-trap-oid ".1.3.6.1.4.1.49739.2.7.0.14";
    dn-events-extensions:event-snmp-trap-vars
      "entPhysicalContainedIn.CONVERTIDX(transcvIAddr,{if-name}) CONVERTIDX(transcvIAddrCont,{if-name});
       dnHwMonTransceiverChannelRxPowerValue.CONVERTIDX(transcvIAddr,{if-name},{channel-id}) {current-rx-power-snmp};
       dnHwMonTransceiverRxPowerLowWarningThreshold.CONVERTIDX(transcvIAddr,{if-name}) {receive-power-warning-low};
       dnHwMonTransceiverRxPowerLowAlarmThreshold.CONVERTIDX(transcvIAddr,{if-name}) {receive-power-alarm-low}";
    leaf if-name {
      type string;
      description
        "Interface name";
    }
    leaf channel-id {
      type uint16;
      description
        "Transceiver channel ID";
    }
    leaf current-rx-power {
      type string;
      description
        "Current RX power in dBm";
    }
    leaf current-rx-power-snmp {
      type ieeefloat32;
      description
        "Current RX power in dBm";
    }
    leaf receive-power-warning-low {
      type int32;
      description
        "Transceiver's input power warning low thershold in dBm";
    }
    leaf receive-power-alarm-low {
      type int32;
      description
        "Transceiver's input power alarm low thershold in dBm";
    }
  }

  notification PLATFORM_TRANSCEIVER_TX_LOW_ALARM {
    description
      "The transceiver output of the indicated interface is too low and at alarm level.";
    dn-events-extensions:event-severity-level "Warning";
    dn-events-extensions:event-message-string "Interface {if-name} transceiver channel ID {channel-id} output power is below threshold {transmit-power-alarm-low} dBm. Current TX power is {current-tx-power} dBm";
    dn-events-extensions:event-corrective-action-string "Check the fiber or transceivers on both sides.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-low {
      type int32;
      description
        "Transceiver's output power warning low thershold in dBm";
    }
    leaf transmit-power-alarm-low {
      type int32;
      description
        "Transceiver's output power alarm low thershold in dBm";
    }
  }

  notification PLATFORM_TRANSCEIVER_MISCONFIGURATION {
    description
      "Optical transceiver misconfiguration detected.";
    dn-events-extensions:event-severity-level "Warning";
    dn-events-extensions:event-message-string "Misconfiguration detected on Interface {if-name}. Reason: {misconfig-type}";
    dn-events-extensions:event-corrective-action-string "Check transceiver configuration settings.";
    dn-events-extensions:event-trigger-component-string "WB Agent";
    dn-events-extensions:event-group "Platform";
    leaf if-name {
      type string;
      description
        "Interface name";
    }
    leaf misconfig-type {
      type enumeration {
        enum unsupported_grid;
        enum unsupported_application;
        enum frequency_oor;
        enum tx_power_oor;
      }
      description
        "Misconfiguration type";
    }
  }

  notification PLATFORM_TRANSCEIVER_CONFIGURATION_ERROR {
    description
      "Optical transceiver configuration error status returned.";
    dn-events-extensions:event-severity-level "Error";
    dn-events-extensions:event-message-string "Interface {if-name} transceiver configuration error status returned. Reason: {error-message}";
    dn-events-extensions:event-corrective-action-string "Check the fiber or transceivers on both sides.";
    dn-events-extensions:event-trigger-component-string "WB Agent";
    dn-events-extensions:event-group "Platform";
    leaf if-name {
      type string;
      description
        "Interface name";
    }
    leaf error-message {
      type enumeration {
        enum tx_power_oor;
        enum fine_tuning_oor;
        enum tuning_rejected;
        enum invalid_channel;
        enum other_hw_error;
      }
      description
        "Type of configuration error";
    }
  }

  notification PLATFORM_TRANSCEIVER_TX_LOW_ALARM_CLEAR {
    description
      "The transceiver low output power alarm of the indicated interface is cleared.";
    dn-events-extensions:event-severity-level "Info";
    dn-events-extensions:event-message-string "Interface {if-name} transceiver channel ID {channel-id} low output power alarm is cleared. Current TX power is {current-tx-power}";
    dn-events-extensions:event-corrective-action-string "No corrective action.";
    dn-events-extensions:event-trigger-component-string "WB Agent";
    dn-events-extensions:event-group "Platform";
    leaf if-name {
      type string;
      description
        "Interface name";
    }
    leaf channel-id {
      type uint16;
      description
        "Transceiver channel ID";
    }
    leaf current-tx-power {
      type string;
      description
        "Current TX power in dBm";
    }
    leaf current-tx-power-snmp {
      type ieeefloat32;
      description
        "Current TX power in dBm";
    }
    leaf transmit-power-warning-low {
      type int32;
      description
        "Transceiver's output power warning low thershold in dBm";
    }
    leaf transmit-power-alarm-low {
      type int32;
      description
        "Transceiver's output power alarm low thershold in dBm";
    }
  }

  notification PLATFORM_TRANSCEIVER_LPMODE_CHANGE_ATTEMPT_DETECTED {
    description
      "Transceiver low power mode bit modification attempt was detected.";
    dn-events-extensions:event-severity-level "Warning";
    dn-events-extensions:event-message-string "An attempt to modify transceiver low-power mode bit was detected on Interface {if-name}. Monitor register value: {reg-value}.";
    dn-events-extensions:event-corrective-action-string "Run the command 'request system techsupport' and contact Customer Support.";
    dn-events-extensions:event-trigger-component-string "WB Agent";
    dn-events-extensions:event-group "Platform";
    leaf if-name {
      type string;
      description
        "Interface name";
    }
    leaf reg-value {
      type string;
      description
        "Monitor register value";
    }
  }

  notification PLATFORM_CPLD_RESET_CONTROL_CHANGE_ATTEMPT_DETECTED {
    description
      "CPLD Reset control registers modification attempt was detected.";
    dn-events-extensions:event-severity-level "Warning";
    dn-events-extensions:event-message-string "An attempt to modify {node-type} {node-id} CPLD {cpld-addr} reset control register {reg-addr} was detected. Monitor register value: {reg-value}.";
    dn-events-extensions:event-corrective-action-string "Run the command 'request system techsupport' and contact Customer Support.";
    dn-events-extensions:event-trigger-component-string "WB Agent";
    dn-events-extensions:event-group "Platform";
    leaf node-type {
      type string;
      description
        "Node type";
    }
    leaf node-id {
      type string;
      description
        "Node ID";
    }
    leaf cpld-addr {
      type string;
      description
        "CPLD address";
    }
    leaf reg-addr {
      type string;
      description
        "Reset control register address";
    }
    leaf reg-value {
      type string;
      description
        "Monitor register value";
    }
  }

  notification PLATFORM_FAN_FAILED {
    description
      "The platform fan has failed, the remaining fans will increase speed to compensate.";
    dn-events-extensions:event-severity-level "Error";
    dn-events-extensions:event-message-string "Fan {fan-id} in {node-type} {node-id} has failed";
    dn-events-extensions:event-corrective-action-string "Replace or fix the failed fan.";
    dn-events-extensions:event-trigger-component-string "WB Agent";
    dn-events-extensions:event-group "Platform";
    dn-events-extensions:event-snmp-trap-name "dnHwMonFanFailed";
    dn-events-extensions:event-snmp-trap-oid ".1.3.6.1.4.1.49739.2.7.0.3";
    dn-events-extensions:event-snmp-trap-vars "entPhysicalContainedIn.CONVERTIDX(fanID,{node-type},{node-id},{fan-id-int}) CONVERTIDX(fanSlotID,{node-type},{node-id},{fan-id-int})";
    leaf fan-id {
      type string;
      description
        "Fan ID";
    }
    leaf fan-id-int {
      type uint16;
      description
        "Fan ID integer";
    }
    leaf node-type {
      type string;
      description
        "Node type";
    }
    leaf node-id {
      type string;
      description
        "Node ID";
    }
  }

  notification PLATFORM_FAN_INSERTED {
    description
      "A fan module was added to the indicated node.";
    dn-events-extensions:event-severity-level "Info";
    dn-events-extensions:event-message-string "Fan {fan-id} in {node-type} {node-id} was inserted";
    dn-events-extensions:event-corrective-action-string "This is informational, no corrective action required.";
    dn-events-extensions:event-trigger-component-string "WB Agent";
    dn-events-extensions:event-group "Platform";
    dn-events-extensions:event-snmp-trap-name "dnFruInserted";
    dn-events-extensions:event-snmp-trap-oid ".1.3.6.1.4.1.49739.2.6.0.2";
    dn-events-extensions:event-snmp-trap-vars "entPhysicalContainedIn.CONVERTIDX(fanID,{node-type},{node-id},{fan-id-int}) CONVERTIDX(fanSlotID,{node-type},{node-id},{fan-id-int})";
    leaf fan-id {
      type string;
      description
        "Fan ID";
    }
    leaf fan-id-int {
      type uint16;
      description
        "Fan ID integer";
    }
    leaf node-type {
      type string;
      description
        "Node type";
    }
    leaf node-id {
      type string;
      description
        "Node ID";
    }
  }

  notification PLATFORM_FAN_REMOVED {
    description
      "A fan module in the indicated node was removed.";
    dn-events-extensions:event-severity-level "Warning";
    dn-events-extensions:event-message-string "Fan {fan-id} in {node-type} {node-id} has removed";
    dn-events-extensions:event-corrective-action-string "Reconnect or replace the fan.";
    dn-events-extensions:event-trigger-component-string "WB Agent";
    dn-events-extensions:event-group "Platform";
    dn-events-extensions:event-snmp-trap-name "dnFruRemoved";
    dn-events-extensions:event-snmp-trap-oid ".1.3.6.1.4.1.49739.2.6.0.1";
    dn-events-extensions:event-snmp-trap-vars "entPhysicalContainedIn.CONVERTIDX(fanID,{node-type},{node-id},{fan-id-int}) CONVERTIDX(fanSlotID,{node-type},{node-id},{fan-id-int})";
    leaf fan-id {
      type string;
      description
        "Fan ID";
    }
    leaf fan-id-int {
      type uint16;
      description
        "Fan ID integer";
    }
    leaf node-type {
      type string;
      description
        "Node type";
    }
    leaf node-id {
      type string;
      description
        "Node ID";
    }
  }

  notification PLATFORM_PSU_INSERTED {
    description
      "A platform Power Supply Unit (PSU) module was added to the indicated node.";
    dn-events-extensions:event-severity-level "Info";
    dn-events-extensions:event-message-string "PSU {psu-id} in {node-type} {node-id} was inserted";
    dn-events-extensions:event-corrective-action-string "This is informational, no corrective action required.";
    dn-events-extensions:event-trigger-component-string "WB Agent";
    dn-events-extensions:event-group "Platform";
    dn-events-extensions:event-snmp-trap-name "dnFruInserted";
    dn-events-extensions:event-snmp-trap-oid ".1.3.6.1.4.1.49739.2.6.0.2";
    dn-events-extensions:event-snmp-trap-vars "entPhysicalContainedIn.CONVERTIDX(psuID,{node-type},{node-id},{psu-id}) CONVERTIDX(psuSlotID,{node-type},{node-id},{psu-id})";
    leaf psu-id {
      type uint16;
      description
        "Power supply unit identification";
    }
    leaf node-type {
      type string;
      description
        "Node type";
    }
    leaf node-id {
      type string;
      description
        "Node ID";
    }
  }

  notification PLATFORM_PSU_REMOVED {
    description
      "A platform Power Supply Unit (PSU) module in the indicated node was removed.";
    dn-events-extensions:event-severity-level "Warning";
    dn-events-extensions:event-message-string "PSU {psu-id} in {node-type} {node-id} has removed";
    dn-events-extensions:event-corrective-action-string "Reconnect or replace the PSU.";
    dn-events-extensions:event-trigger-component-string "WB Agent";
    dn-events-extensions:event-group "Platform";
    dn-events-extensions:event-snmp-trap-name "dnFruRemoved";
    dn-events-extensions:event-snmp-trap-oid ".1.3.6.1.4.1.49739.2.6.0.1";
    dn-events-extensions:event-snmp-trap-vars "entPhysicalContainedIn.CONVERTIDX(psuID,{node-type},{node-id},{psu-id}) CONVERTIDX(psuSlotID,{node-type},{node-id},{psu-id})";
    leaf psu-id {
      type uint16;
      description
        "Power supply unit identification";
    }
    leaf node-type {
      type string;
      description
        "Node type";
    }
    leaf node-id {
      type string;
      description
        "Node ID";
    }
  }

  notification PLATFORM_PSU_FAN_FAILED {
    description
      "The platform Power Supply Unit (PSU) fan has failed.";
    dn-events-extensions:event-severity-level "Error";
    dn-events-extensions:event-message-string "Fan {fan-id} of PSU {psu-id} in {node-type} {node-id} has failed";
    dn-events-extensions:event-corrective-action-string "Replace or fix the failed fan or replace the PSU.";
    dn-events-extensions:event-trigger-component-string "Node Manager";
    dn-events-extensions:event-group "Platform";
    dn-events-extensions:event-snmp-trap-name "dnHwMonFanFailed";
    dn-events-extensions:event-snmp-trap-oid ".1.3.6.1.4.1.49739.2.7.0.3";
    dn-events-extensions:event-snmp-trap-vars "entPhysicalContainedIn.CONVERTIDX(psuFanID,{node-type},{node-id},{psu-id},{fan-id}) CONVERTIDX(psuID,{node-type},{node-id},{psu-id})";
    leaf psu-id {
      type uint16;
      description
        "Power supply unit identification";
    }
    leaf fan-id {
      type uint16;
      description
        "Fan ID";
    }
    leaf node-type {
      type string;
      description
        "Node type";
    }
    leaf node-id {
      type string;
      description
        "Node ID";
    }
  }

  notification PLATFORM_FAN_STATE_CHANGE {
    description
      "The platform fan operational state has changed.";
    dn-events-extensions:event-severity-level "Info";
    dn-events-extensions:event-message-string "Fan {fan-id} in {node-type} {node-id} state changed to {current-state}";
    dn-events-extensions:event-corrective-action-string "This is informational, no corrective action required.";
    dn-events-extensions:event-trigger-component-string "WB Agent";
    dn-events-extensions:event-group "Platform";
    dn-events-extensions:event-snmp-trap-name "dnHwMonFanStateChange";
    dn-events-extensions:event-snmp-trap-oid ".1.3.6.1.4.1.49739.2.7.0.4";
    dn-events-extensions:event-snmp-trap-vars
      "entPhysicalContainedIn.CONVERTIDX(fanID,{node-type},{node-id},{fan-id-int}) CONVERTIDX(fanSlotID,{node-type},{node-id},{fan-id-int});
       dnHwMonFanOperStatus.CONVERTIDX(fanID,{node-type},{node-id},{fan-id-int}) CONVERT fanOpStC {current-state}";
    leaf fan-id {
      type string;
      description
        "Fan ID";
    }
    leaf fan-id-int {
      type uint16;
      description
        "Fan ID integer";
    }
    leaf node-type {
      type string;
      description
        "Node type";
    }
    leaf node-id {
      type string;
      description
        "Node ID";
    }
    leaf current-state {
      type string;
      description
        "Current fan operational state";
    }
  }

  notification PLATFORM_PSU_FAN_STATE_CHANGE {
    description
      "The platform Power Supply Unit (PSU) fan operational state has changed.";
    dn-events-extensions:event-severity-level "Info";
    dn-events-extensions:event-message-string "Fan {fan-id} of PSU {psu-id} in {node-type} {node-id} state changed to {current-state}";
    dn-events-extensions:event-corrective-action-string "This is informational, no corrective action required.";
    dn-events-extensions:event-trigger-component-string "WB Agent";
    dn-events-extensions:event-group "Platform";
    dn-events-extensions:event-snmp-trap-name "dnHwMonFanStateChange";
    dn-events-extensions:event-snmp-trap-oid ".1.3.6.1.4.1.49739.2.7.0.4";
    dn-events-extensions:event-snmp-trap-vars
      "entPhysicalContainedIn.CONVERTIDX(psuFanID,{node-type},{node-id},{psu-id},{fan-id}) CONVERTIDX(psuID,{node-type},{node-id},{psu-id});
       dnHwMonFanOperStatus.CONVERTIDX(psuFanID,{node-type},{node-id},{psu-id},{fan-id}) CONVERT fanOpStC {current-state}";
    leaf psu-id {
      type uint16;
      description
        "Power supply unit identification";
    }
    leaf fan-id {
      type uint16;
      description
        "Fan ID";
    }
    leaf node-type {
      type string;
      description
        "Node type";
    }
    leaf node-id {
      type string;
      description
        "Node ID";
    }
    leaf current-state {
      type string;
      description
        "Current fan operational state";
    }
  }

  notification PLATFORM_FAN_MAX_SPEED_REACHED {
    description
      "The platform fans are at the maximum speed and crossed the temperature threshold.";
    dn-events-extensions:event-severity-level "Notice";
    dn-events-extensions:event-message-string "All fans in {node-type} {node-id} have reached the maximum speed and crossed the temperature sensor threshold. Temperature sensor {sensor-name} threshold warning value {actual-warning-threshold} {temperature-type}. Temperature value of the sensor is {temperature-value} {temperature-type}";
    dn-events-extensions:event-corrective-action-string "Check the temperature of the nodes environment. If the fan has failed, replace, or fix the failed fan.";
    dn-events-extensions:event-trigger-component-string "WB Agent";
    dn-events-extensions:event-group "Platform";
    leaf node-type {
      type string;
      description
        "Node type";
    }
    leaf node-id {
      type string;
      description
        "Node ID";
    }
    leaf sensor-name {
      type string;
      description
        "Temperature sensor name";
    }
    leaf temperature-value {
      type string;
      description
        "Current measured temperature value";
    }
    leaf temperature-type {
      type string;
      description
        "Celsius / Fahrenheit";
    }
    leaf actual-warning-threshold {
      type int32;
      description
        "Actual temperature threshold of the sensor causing the fans to reach 100% speed";
    }
  }

  notification PLATFORM_FAN_MAX_SPEED_CLEARED {
    description
      "The platform fans have moved below the maximum speed.";
    dn-events-extensions:event-severity-level "Info";
    dn-events-extensions:event-message-string "All fans in {node-type} {node-id} have moved below the maximum speed as the temperature is less than the maximum temperature sensor threshold";
    dn-events-extensions:event-corrective-action-string "This is informational, no corrective action required.";
    dn-events-extensions:event-trigger-component-string "WB Agent";
    dn-events-extensions:event-group "Platform";
    leaf node-type {
      type string;
      description
        "Node type";
    }
    leaf node-id {
      type string;
      description
        "Node ID";
    }
  }

  notification PLATFORM_PSU_FAILED {
    description
      "The platform Power Supply Unit (PSU) has failed.";
    dn-events-extensions:event-severity-level "Error";
    dn-events-extensions:event-message-string "PSU {psu-id} in {node-type} {node-id} has failed";
    dn-events-extensions:event-corrective-action-string "Replace or fix the failed PSU.";
    dn-events-extensions:event-trigger-component-string "WB Agent";
    dn-events-extensions:event-group "Platform";
    dn-events-extensions:event-snmp-trap-name "dnHwMonPsuFailed";
    dn-events-extensions:event-snmp-trap-oid ".1.3.6.1.4.1.49739.2.7.0.1";
    dn-events-extensions:event-snmp-trap-vars "entPhysicalContainedIn.CONVERTIDX(psuID,{node-type},{node-id},{psu-id}) CONVERTIDX(psuSlotID,{node-type},{node-id},{psu-id})";
    leaf psu-id {
      type uint16;
      description
        "Power supply unit identification";
    }
    leaf node-type {
      type string;
      description
        "Node type";
    }
    leaf node-id {
      type string;
      description
        "Node ID";
    }
  }

  notification PLATFORM_PSU_STATE_CHANGE {
    description
      "The platform Power Supply Unit (PSU) operational state has changed.";
    dn-events-extensions:event-severity-level "Info";
    dn-events-extensions:event-message-string "PSU {psu-id} in {node-type} {node-id} state changed to {current-state}";
    dn-events-extensions:event-corrective-action-string "This is informational, no corrective action required.";
    dn-events-extensions:event-trigger-component-string "WB Agent";
    dn-events-extensions:event-group "Platform";
    dn-events-extensions:event-snmp-trap-name "dnHwMonPsuStateChange";
    dn-events-extensions:event-snmp-trap-oid ".1.3.6.1.4.1.49739.2.7.0.2";
    dn-events-extensions:event-snmp-trap-vars
      "entPhysicalContainedIn.CONVERTIDX(psuID,{node-type},{node-id},{psu-id}) CONVERTIDX(psuSlotID,{node-type},{node-id},{psu-id});
       dnHwMonPsuOperStatus.CONVERTIDX(psuID,{node-type},{node-id},{psu-id}) CONVERT psuOpStC {current-state}";
    leaf psu-id {
      type uint16;
      description
        "Power supply unit identification";
    }
    leaf node-type {
      type string;
      description
        "Node type";
    }
    leaf node-id {
      type string;
      description
        "Node ID";
    }
    leaf current-state {
      type string;
      description
        "Current fan operational state";
    }
  }

  notification PLATFORM_PSU_INPUT_VOLTAGE_NORMAL {
    description
      "The listed platform Power Supply Unit (PSU) input voltage has returned to normal. This event is only displayed if previously the platform input voltage was either too high or too low.";
    dn-events-extensions:event-severity-level "Info";
    dn-events-extensions:event-message-string "PSU {psu-id} in {node-type} {node-id} input voltage is normal. Current input voltage is {current-input-voltage}";
    dn-events-extensions:event-corrective-action-string "No corrective action.";
    dn-events-extensions:event-trigger-component-string "WB Agent";
    dn-events-extensions:event-group "Platform";
    dn-events-extensions:event-snmp-trap-name "dnHwMonPsuInputVoltageNormal";
    dn-events-extensions:event-snmp-trap-oid ".1.3.6.1.4.1.49739.2.7.0.9";
    dn-events-extensions:event-snmp-trap-vars
      "entPhysicalContainedIn.CONVERTIDX(psuID,{node-type},{node-id},{psu-id}) CONVERTIDX(psuSlotID,{node-type},{node-id},{psu-id});
       dnHwMonPsuInputVoltageValue.CONVERTIDX(psuID,{node-type},{node-id},{psu-id}) {current-input-voltage-snmp}";
    leaf psu-id {
      type uint16;
      description
        "Power supply unit identification";
    }
    leaf node-type {
      type string;
      description
        "Node type";
    }
    leaf node-id {
      type string;
      description
        "Node ID";
    }
    leaf current-input-voltage {
      type string;
      description
        "Current input voltage in volts";
    }
    leaf current-input-voltage-snmp {
      type string;
      description
        "Current input voltage in volts";
    }
  }

  notification PLATFORM_PSU_INPUT_VOLTAGE_HIGH {
    description
      "The Power Supply Unit (PSU) of the listed NCP or NCF has an input voltage that is too high.";
    dn-events-extensions:event-severity-level "Warning";
    dn-events-extensions:event-message-string "PSU {psu-id} in {node-type} {node-id} input voltage is too high. Current input voltage is {current-input-voltage}";
    dn-events-extensions:event-corrective-action-string "Check power supply input to the PSU.";
    dn-events-extensions:event-trigger-component-string "WB Agent";
    dn-events-extensions:event-group "Platform";
    dn-events-extensions:event-snmp-trap-name "dnHwMonPsuInputVoltageHigh";
    dn-events-extensions:event-snmp-trap-oid ".1.3.6.1.4.1.49739.2.7.0.8";
    dn-events-extensions:event-snmp-trap-vars
      "entPhysicalContainedIn.CONVERTIDX(psuID,{node-type},{node-id},{psu-id}) CONVERTIDX(psuSlotID,{node-type},{node-id},{psu-id});
       dnHwMonPsuInputVoltageValue.CONVERTIDX(psuID,{node-type},{node-id},{psu-id}) {current-input-voltage-snmp}";
    leaf psu-id {
      type uint16;
      description
        "Power supply unit identification";
    }
    leaf node-type {
      type string;
      description
        "Node type";
    }
    leaf node-id {
      type string;
      description
        "Node ID";
    }
    leaf current-input-voltage {
      type string;
      description
        "Current input voltage in volts";
    }
    leaf current-input-voltage-snmp {
      type string;
      description
        "Current input voltage in volts";
    }
  }

  notification PLATFORM_PSU_INPUT_VOLTAGE_LOW {
    description
      "The Power Supply Unit (PSU) of the listed NCP or NCF has an input voltage that is too low.";
    dn-events-extensions:event-severity-level "Warning";
    dn-events-extensions:event-message-string "PSU {psu-id} in {node-type} {node-id} input voltage is too low. Current input voltage is {current-input-voltage}";
    dn-events-extensions:event-corrective-action-string "Check power supply input to the PSU.";
    dn-events-extensions:event-trigger-component-string "WB Agent";
    dn-events-extensions:event-group "Platform";
    dn-events-extensions:event-snmp-trap-name "dnHwMonPsuInputVoltageLow";
    dn-events-extensions:event-snmp-trap-oid ".1.3.6.1.4.1.49739.2.7.0.7";
    dn-events-extensions:event-snmp-trap-vars
      "entPhysicalContainedIn.CONVERTIDX(psuID,{node-type},{node-id},{psu-id}) CONVERTIDX(psuSlotID,{node-type},{node-id},{psu-id});
       dnHwMonPsuInputVoltageValue.CONVERTIDX(psuID,{node-type},{node-id},{psu-id}) {current-input-voltage-snmp}";
    leaf psu-id {
      type uint16;
      description
        "Power supply unit identification";
    }
    leaf node-type {
      type string;
      description
        "Node type";
    }
    leaf node-id {
      type string;
      description
        "Node ID";
    }
    leaf current-input-voltage {
      type string;
      description
        "Current input voltage in volts";
    }
    leaf current-input-voltage-snmp {
      type string;
      description
        "Current input voltage in volts";
    }
  }

  notification PLATFORM_PSU_OUTPUT_VOLTAGE_NORMAL {
    description
      "The listed platform Power Supply Unit (PSU) output voltage has returned to normal. This event is only displayed if previously the platform output voltage was either too high or too low.";
    dn-events-extensions:event-severity-level "Info";
    dn-events-extensions:event-message-string "PSU {psu-id} in {node-type} {node-id} output voltage is normal. Current output voltage is {current-output-voltage}";
    dn-events-extensions:event-corrective-action-string "No corrective action.";
    dn-events-extensions:event-trigger-component-string "WB Agent";
    dn-events-extensions:event-group "Platform";
    leaf psu-id {
      type uint16;
      description
        "Power supply unit identification";
    }
    leaf node-type {
      type string;
      description
        "Node type";
    }
    leaf node-id {
      type string;
      description
        "Node ID";
    }
    leaf current-output-voltage {
      type string;
      description
        "Current output voltage in volts";
    }
  }

  notification PLATFORM_PSU_OUTPUT_VOLTAGE_HIGH {
    description
      "The Power Supply Unit (PSU) of the listed node has an output voltage that is too high.";
    dn-events-extensions:event-severity-level "Warning";
    dn-events-extensions:event-message-string "PSU {psu-id} in {node-type} {node-id} output voltage is too high. Current output voltage is {current-output-voltage}, output voltage high warning threshold is {output-voltage-high-threshold}";
    dn-events-extensions:event-corrective-action-string "Check the power supply input to the PSU.";
    dn-events-extensions:event-trigger-component-string "WB Agent";
    dn-events-extensions:event-group "Platform";
    leaf psu-id {
      type uint16;
      description
        "Power supply unit identification";
    }
    leaf node-type {
      type string;
      description
        "Node type";
    }
    leaf node-id {
      type string;
      description
        "Node ID";
    }
    leaf current-output-voltage {
      type string;
      description
        "Current output voltage in volts";
    }
    leaf output-voltage-high-threshold {
      type string;
      description
        "Output voltage high warning threshold in volts";
    }
  }

  notification PLATFORM_PSU_OUTPUT_VOLTAGE_LOW {
    description
      "The Power Supply Unit (PSU) of the listed node has an output voltage that is too low.";
    dn-events-extensions:event-severity-level "Warning";
    dn-events-extensions:event-message-string "PSU {psu-id} in {node-type} {node-id} output voltage is too low. Current output voltage is {current-output-voltage}, output voltage low warning threshold is {output-voltage-low-threshold}";
    dn-events-extensions:event-corrective-action-string "Check the power supply input to the PSU.";
    dn-events-extensions:event-trigger-component-string "WB Agent";
    dn-events-extensions:event-group "Platform";
    leaf psu-id {
      type uint16;
      description
        "Power supply unit identification";
    }
    leaf node-type {
      type string;
      description
        "Node type";
    }
    leaf node-id {
      type string;
      description
        "Node ID";
    }
    leaf current-output-voltage {
      type string;
      description
        "Current output voltage in volts";
    }
    leaf output-voltage-low-threshold {
      type string;
      description
        "Output voltage low warning threshold in volts";
    }
  }

  notification PLATFORM_TEMP_SENSOR_STATE_CHANGE {
    description
      "The temperature sensor state changed.";
    dn-events-extensions:event-severity-level "Warning";
    dn-events-extensions:event-message-string "Temperature sensor {sensor-name} in {node-type} {node-id} state changed to {current-state}. Temperature value of the sensor is {temperature-value} {temperature-type}";
    dn-events-extensions:event-corrective-action-string "Check the node environment to identify a cause of the temperature change.";
    dn-events-extensions:event-trigger-component-string "WB Agent";
    dn-events-extensions:event-group "Platform";
    dn-events-extensions:event-snmp-trap-name "dnHwMonTemperatureStateChange";
    dn-events-extensions:event-snmp-trap-oid ".1.3.6.1.4.1.49739.2.7.0.5";
    dn-events-extensions:event-snmp-trap-vars
      "entPhysicalContainedIn.CONVERTIDX(tempSensorID,{node-type},{node-id},{sensor-index}) CONVERT nodeID({node-type}) {node-id};
       dnHwMonTemperatureStatus.CONVERTIDX(tempSensorID,{node-type},{node-id},{sensor-index}) CONVERT sensorOpStC {current-state};
       dnHwMonTemperatureValue.CONVERTIDX(tempSensorID,{node-type},{node-id},{sensor-index}) {temperature-value-snmp};
       dnHwMonTemperatureHighCriticalThreshold.CONVERTIDX(tempSensorID,{node-type},{node-id},{sensor-index}) {high-critical-threshold};
       dnHwMonTemperatureHighWarningThreshold.CONVERTIDX(tempSensorID,{node-type},{node-id},{sensor-index}) {high-warning-threshold}";
    leaf sensor-name {
      type string;
      description
        "Temperature sensor name";
    }
    leaf node-type {
      type string;
      description
        "Node type";
    }
    leaf node-id {
      type string;
      description
        "Node ID";
    }
    leaf current-state {
      type string;
      description
        "Current sensor operational state";
    }
    leaf temperature-value {
      type string;
      description
        "Current measured temperature value";
    }
    leaf temperature-type {
      type string;
      description
        "Celsius / Fahrenheit";
    }
    leaf sensor-index {
      type uint16;
      description
        "Temperature sensor running index";
    }
    leaf temperature-value-snmp {
      type ieeefloat32;
      description
        "Current measured temperature value in degrees Celsius";
    }
    leaf high-warning-threshold {
      type int32;
      description
        "High warning temperature threshold of the sensor in degrees Celsius";
    }
    leaf high-critical-threshold {
      type int32;
      description
        "High critical temperature threshold of the sensor in degrees Celsius";
    }
  }

  notification PLATFORM_TEMP_SENSOR_STATE_CHANGE_NORMAL {
    description
      "The temperature sensor state changed to normal.";
    dn-events-extensions:event-severity-level "Info";
    dn-events-extensions:event-message-string "Temperature sensor {sensor-name} in {node-type} {node-id} state changed to {current-state}. Temperature value of the sensor is {temperature-value} {temperature-type}";
    dn-events-extensions:event-corrective-action-string "This is informational, no corrective action required.";
    dn-events-extensions:event-trigger-component-string "WB Agent";
    dn-events-extensions:event-group "Platform";
    dn-events-extensions:event-snmp-trap-name "dnHwMonTemperatureNormal";
    dn-events-extensions:event-snmp-trap-oid ".1.3.6.1.4.1.49739.2.7.0.6";
    dn-events-extensions:event-snmp-trap-vars
      "entPhysicalContainedIn.CONVERTIDX(tempSensorID,{node-type},{node-id},{sensor-index}) CONVERT nodeID({node-type}) {node-id};
       dnHwMonTemperatureStatus.CONVERTIDX(tempSensorID,{node-type},{node-id},{sensor-index}) CONVERT sensorOpStC {current-state};
       dnHwMonTemperatureValue.CONVERTIDX(tempSensorID,{node-type},{node-id},{sensor-index}) {temperature-value-snmp}";
    leaf sensor-name {
      type string;
      description
        "Temperature sensor name";
    }
    leaf node-type {
      type string;
      description
        "Node type";
    }
    leaf node-id {
      type string;
      description
        "Node ID";
    }
    leaf current-state {
      type string;
      description
        "Current sensor operational state";
    }
    leaf temperature-value {
      type string;
      description
        "Current measured temperature value";
    }
    leaf temperature-type {
      type string;
      description
        "Celsius / Fahrenheit";
    }
    leaf sensor-index {
      type uint16;
      description
        "Temperature sensor running index";
    }
    leaf temperature-value-snmp {
      type ieeefloat32;
      description
        "Current measured temperature value in degrees Celsius";
    }
  }

  notification PLATFORM_USB_ADMIN_STATE_CONFIG {
    description
      "A user has changed the admin-state on the USB port.";
    dn-events-extensions:event-severity-level "Info";
    dn-events-extensions:event-message-string "User {user-name} changed the USB port {usb-port-name} in {node-type} {node-id} admin-state configuration to {new-state}";
    dn-events-extensions:event-corrective-action-string "This is informational, no corrective action required.";
    dn-events-extensions:event-trigger-component-string "Transaction-manager";
    dn-events-extensions:event-group "Platform";
    leaf user-name {
      type string;
      description
        "User name";
    }
    leaf usb-port-name {
      type string;
      description
        "USB port name";
    }
    leaf node-type {
      type string;
      description
        "Node type";
    }
    leaf node-id {
      type string;
      description
        "Node ID";
    }
    leaf new-state {
      type string;
      description
        "USB new state";
    }
  }

  notification PLATFORM_USB_REMOVED {
    description
      "A USB drive was removed from the USB port.";
    dn-events-extensions:event-severity-level "Warning";
    dn-events-extensions:event-message-string "A USB drive was removed from USB port {usb-port-name} in {node-type} {node-id}";
    dn-events-extensions:event-corrective-action-string "No corrective action.";
    dn-events-extensions:event-trigger-component-string "WB Agent";
    dn-events-extensions:event-group "Platform";
    leaf usb-port-name {
      type string;
      description
        "Interface name";
    }
    leaf node-type {
      type string;
      description
        "Node type";
    }
    leaf node-id {
      type string;
      description
        "Node ID";
    }
  }

  notification PLATFORM_USB_INSERTED {
    description
      "A USB drive was inserted into the USB port.";
    dn-events-extensions:event-severity-level "Notice";
    dn-events-extensions:event-message-string "A USB drive was inserted into USB port {usb-port-name} in {node-type} {node-id}";
    dn-events-extensions:event-corrective-action-string "No corrective action.";
    dn-events-extensions:event-trigger-component-string "WB Agent";
    dn-events-extensions:event-group "Platform";
    leaf usb-port-name {
      type string;
      description
        "Interface name";
    }
    leaf node-type {
      type string;
      description
        "Node type";
    }
    leaf node-id {
      type string;
      description
        "Node ID";
    }
  }

  notification PLATFORM_CPU_LIMIT_CLEARED {
    description
      "The CPU of the node listed has moved below the maximum limit of 90%.";
    dn-events-extensions:event-severity-level "Info";
    dn-events-extensions:event-message-string "CPU in {node-type} {node-id} has moved below the maximum limit of {limit}%";
    dn-events-extensions:event-corrective-action-string "This is informational, no corrective action required.";
    dn-events-extensions:event-trigger-component-string "WB Agent";
    dn-events-extensions:event-group "Platform";
    leaf node-type {
      type string;
      description
        "Node type";
    }
    leaf node-id {
      type uint16;
      description
        "Node ID";
    }
    leaf limit {
      type uint16;
      description
        "Limit in percent";
    }
  }

  notification PLATFORM_CPU_LIMIT_REACHED {
    description
      "The CPU of the node listed has reached the maximum limit of 90%.";
    dn-events-extensions:event-severity-level "Error";
    dn-events-extensions:event-message-string "CPU in {node-type} {node-id} has reached its maximum limit of {limit}%";
    dn-events-extensions:event-corrective-action-string "Remove redundant applications being used.";
    dn-events-extensions:event-trigger-component-string "WB Agent";
    dn-events-extensions:event-group "Platform";
    leaf node-type {
      type string;
      description
        "Node type";
    }
    leaf node-id {
      type uint16;
      description
        "Node ID";
    }
    leaf limit {
      type uint16;
      description
        "Limit in percent";
    }
  }

  notification PLATFORM_CPU_THRESHOLD_CLEARED {
    description
      "The CPU of the node listed is below the threshold.";
    dn-events-extensions:event-severity-level "Info";
    dn-events-extensions:event-message-string "CPU in {node-type} {node-id} is below the threshold ({threshold}%)";
    dn-events-extensions:event-corrective-action-string "This is informational, no corrective action required.";
    dn-events-extensions:event-trigger-component-string "WB Agent";
    dn-events-extensions:event-group "Platform";
    dn-events-extensions:event-snmp-trap-name "dnRsCpuThresholdCleared";
    dn-events-extensions:event-snmp-trap-oid ".1.3.6.1.4.1.49739.2.8.0.2";
    dn-events-extensions:event-snmp-trap-vars "dnRsCpuThreshold.CONVERTIDX(cpuID,{node-type},{node-id}) {threshold} ; dnRsCpu1minAvg.CONVERTIDX(cpuID,{node-type},{node-id}) {utilization-1min-avg}";
    leaf node-type {
      type string;
      description
        "Node type";
    }
    leaf node-id {
      type uint16;
      description
        "Node ID";
    }
    leaf threshold {
      type uint16;
      description
        "Threshold in percent";
    }
    leaf utilization-1min-avg {
      type uint8;
      units "percent";
      description
        "CPU 1-minute average utilization rate in percent";
    }
  }

  notification PLATFORM_CPU_THRESHOLD_EXCEEDED {
    description
      "The CPU of the node listed has crossed the threshold.";
    dn-events-extensions:event-severity-level "Warning";
    dn-events-extensions:event-message-string "CPU in {node-type} {node-id} has exceeded the threshold ({threshold}%)";
    dn-events-extensions:event-corrective-action-string "No corrective action required.";
    dn-events-extensions:event-trigger-component-string "WB Agent";
    dn-events-extensions:event-group "Platform";
    dn-events-extensions:event-snmp-trap-name "dnRsCpuThresholdExceeded";
    dn-events-extensions:event-snmp-trap-oid ".1.3.6.1.4.1.49739.2.8.0.1";
    dn-events-extensions:event-snmp-trap-vars "dnRsCpuThreshold.CONVERTIDX(cpuID,{node-type},{node-id}) {threshold} ; dnRsCpu1minAvg.CONVERTIDX(cpuID,{node-type},{node-id}) {utilization-1min-avg}";
    leaf node-type {
      type string;
      description
        "Node type";
    }
    leaf node-id {
      type uint16;
      description
        "Node ID";
    }
    leaf threshold {
      type uint16;
      description
        "Threshold in percent";
    }
    leaf utilization-1min-avg {
      type uint8;
      units "percent";
      description
        "CPU 1-minute average utilization rate in percent";
    }
  }

  notification PLATFORM_HD_LIMIT_CLEARED {
    description
      "The hard disk partition of the node listed has moved below the limit of 100%.";
    dn-events-extensions:event-severity-level "Info";
    dn-events-extensions:event-message-string "Hard disk partition {partition-name} in {node-type} {node-id} is below the limit, total hard disk partition space is {total-partition-size} MB";
    dn-events-extensions:event-corrective-action-string "This is informational, no corrective action required.";
    dn-events-extensions:event-trigger-component-string "WB Agent";
    dn-events-extensions:event-group "Platform";
    leaf partition-name {
      type string;
      description
        "Partition name";
    }
    leaf node-type {
      type string;
      description
        "Node type";
    }
    leaf node-id {
      type string;
      description
        "Node ID";
    }
    leaf total-partition-size {
      type uint64;
      description
        "Total hard disk partition space in MB";
    }
  }

  notification PLATFORM_HD_LIMIT_REACHED {
    description
      "The hard disk partition of the node listed reached the maximum limit of 100%.";
    dn-events-extensions:event-severity-level "Error";
    dn-events-extensions:event-message-string "Hard disk partition {partition-name} in {node-type} {node-id} reached the limit, maximum hard disk partition space is {total-partition-size} MB";
    dn-events-extensions:event-corrective-action-string "Clear redundant applications or files in use such as log files.";
    dn-events-extensions:event-trigger-component-string "WB Agent";
    dn-events-extensions:event-group "Platform";
    leaf partition-name {
      type string;
      description
        "Partition name";
    }
    leaf node-type {
      type string;
      description
        "Node type";
    }
    leaf node-id {
      type string;
      description
        "Node ID";
    }
    leaf total-partition-size {
      type uint64;
      description
        "Total hard disk partition space in MB";
    }
  }

  notification PLATFORM_HD_THRESHOLD_CLEARED {
    description
      "The hard disk partition of the node listed is below the threshold.";
    dn-events-extensions:event-severity-level "Info";
    dn-events-extensions:event-message-string "Hard disk partition {partition-name} in {node-type} {node-id} is below the threshold ({threshold}%), current usage is {partition-space-value} MB, total hard disk partition available space is {total-partition-size} MB";
    dn-events-extensions:event-corrective-action-string "This is informational, no corrective action required.";
    dn-events-extensions:event-trigger-component-string "WB Agent";
    dn-events-extensions:event-group "Platform";
    leaf partition-name {
      type string;
      description
        "Partition name";
    }
    leaf node-type {
      type string;
      description
        "Node type";
    }
    leaf node-id {
      type string;
      description
        "Node ID";
    }
    leaf total-partition-size {
      type uint64;
      description
        "Maximum hard disk space";
    }
    leaf partition-space-value {
      type uint64;
      description
        "Current hard disk usage";
    }
    leaf threshold {
      type uint16;
      description
        "Threshold in percent";
    }
  }

  notification PLATFORM_HD_THRESHOLD_EXCEEDED {
    description
      "The hard disk partition of the node listed has crossed the threshold.";
    dn-events-extensions:event-severity-level "Warning";
    dn-events-extensions:event-message-string "Hard disk partition {partition-name} in {node-type} {node-id} is above the threshold ({threshold}%), current usage is {partition-space-value} MB, total hard disk partition available space is {total-partition-size} MB";
    dn-events-extensions:event-corrective-action-string "No corrective action required.";
    dn-events-extensions:event-trigger-component-string "WB Agent";
    dn-events-extensions:event-group "Platform";
    leaf partition-name {
      type string;
      description
        "Partition name";
    }
    leaf node-type {
      type string;
      description
        "Node type";
    }
    leaf node-id {
      type string;
      description
        "Node ID";
    }
    leaf total-partition-size {
      type uint64;
      description
        "Maximum hard disk space";
    }
    leaf partition-space-value {
      type uint64;
      description
        "Current hard disk usage";
    }
    leaf threshold {
      type uint16;
      description
        "Threshold in percent";
    }
  }

  notification PLATFORM_DISK_LIFETIME_UTILIZATION_THRESHOLD_EXCEEDED {
    description
      "The disk of the node listed has crossed the lifetime utilization threshold.";
    dn-events-extensions:event-severity-level "Warning";
    dn-events-extensions:event-message-string "Disk {disk-model} with serial number {disk-serial-number} lifetime utilization in {node-type} {node-id} {disk-location} is above the threshold ({threshold}%)";
    dn-events-extensions:event-corrective-action-string "Please schedule replacing the disk soon to prevent data loss.";
    dn-events-extensions:event-trigger-component-string "WB Agent";
    dn-events-extensions:event-group "Platform";
    leaf disk-model {
      type string;
      description
        "Disk model";
    }
    leaf disk-serial-number {
      type string;
      description
        "Disk serial number";
    }
    leaf node-type {
      type string;
      description
        "Node type";
    }
    leaf node-id {
      type string;
      description
        "Node ID";
    }
    leaf disk-location {
      type string;
      description
        "Disk location in the box";
    }
    leaf threshold {
      type uint16;
      description
        "Threshold in percent";
    }
  }

  notification PLATFORM_DISK_LIFETIME_UTILIZATION_LIMIT_REACHED {
    description
      "The disk of the node listed has reached the maximum lifetime utilization of 100%.";
    dn-events-extensions:event-severity-level "Critical";
    dn-events-extensions:event-message-string "Disk {disk-model} with serial number {disk-serial-number} in {node-type} {node-id} {disk-location} reached 100% lifetime utilization limit";
    dn-events-extensions:event-corrective-action-string "Replace Disk to prevent data loss.";
    dn-events-extensions:event-trigger-component-string "WB Agent";
    dn-events-extensions:event-group "Platform";
    leaf disk-model {
      type string;
      description
        "Disk model";
    }
    leaf disk-serial-number {
      type string;
      description
        "Disk serial number";
    }
    leaf node-type {
      type string;
      description
        "Node type";
    }
    leaf node-id {
      type string;
      description
        "Node ID";
    }
    leaf disk-location {
      type string;
      description
        "Disk location in the box";
    }
  }

  notification PLATFORM_DISK_FAILED {
    description
      "The platform disk has failed.";
    dn-events-extensions:event-severity-level "Error";
    dn-events-extensions:event-message-string "Disk {disk-model} with serial number {disk-serial-number} in {node-type} {node-id} {disk-location} has failed";
    dn-events-extensions:event-corrective-action-string "Replace the failing disk.";
    dn-events-extensions:event-trigger-component-string "WB Agent";
    dn-events-extensions:event-group "Platform";
    dn-events-extensions:event-snmp-trap-name "dnHwMonDiskFailed";
    dn-events-extensions:event-snmp-trap-oid ".1.3.6.1.4.1.49739.2.7.0.15";
    dn-events-extensions:event-snmp-trap-vars
      "entPhysicalContainedIn.CONVERTIDX(diskID,{node-type},{node-id},{disk-id}) CONVERTIDX(diskSlotID,{node-type},{node-id},{disk-id});
       dnHwMonDiskLocation.CONVERTIDX(diskID,{node-type},{node-id},{disk-id}) {disk-location}";
    leaf disk-model {
      type string;
      description
        "Disk model";
    }
    leaf disk-serial-number {
      type string;
      description
        "Disk serial number";
    }
    leaf node-type {
      type string;
      description
        "Node type";
    }
    leaf node-id {
      type string;
      description
        "Node ID";
    }
    leaf disk-id {
      type string;
      description
        "Disk index in platform";
    }
    leaf disk-location {
      type string;
      description
        "Disk location in the box";
    }
  }

  notification PLATFORM_MEMORY_LIMIT_CLEARED {
    description
      "The memory in the node listed is below the limit of 100%.";
    dn-events-extensions:event-severity-level "Info";
    dn-events-extensions:event-message-string "Memory in {node-type} {node-id} is below the limit, total memory is {total-memory-value} MB";
    dn-events-extensions:event-corrective-action-string "This is informational, no corrective action required.";
    dn-events-extensions:event-trigger-component-string "WB Agent";
    dn-events-extensions:event-group "Platform";
    leaf node-type {
      type string;
      description
        "Node type";
    }
    leaf node-id {
      type uint16;
      description
        "Node ID";
    }
    leaf total-memory-value {
      type uint64;
      description
        "Total memory";
    }
  }

  notification PLATFORM_MEMORY_LIMIT_REACHED {
    description
      "The memory in the node listed has reached the maximum limit of 100%.";
    dn-events-extensions:event-severity-level "Error";
    dn-events-extensions:event-message-string "Memory in {node-type} {node-id} has reached the limit, total memory is {total-memory-value} MB";
    dn-events-extensions:event-corrective-action-string "Clear redundant applications or files in use such as log files.";
    dn-events-extensions:event-trigger-component-string "WB Agent";
    dn-events-extensions:event-group "Platform";
    leaf node-type {
      type string;
      description
        "Node type";
    }
    leaf node-id {
      type uint16;
      description
        "Node ID";
    }
    leaf total-memory-value {
      type uint64;
      description
        "Total memory";
    }
  }

  notification PLATFORM_MEMORY_THRESHOLD_CLEARED {
    description
      "The memory in the node listed is below the threshold.";
    dn-events-extensions:event-severity-level "Info";
    dn-events-extensions:event-message-string "Memory in {node-type} {node-id} is below the threshold ({threshold}%), current usage is {memory-value} MB , total available memory is {total-memory-value} MB";
    dn-events-extensions:event-corrective-action-string "This is informational, no corrective action required.";
    dn-events-extensions:event-trigger-component-string "WB Agent";
    dn-events-extensions:event-group "Platform";
    dn-events-extensions:event-snmp-trap-name "dnRsMemThresholdCleared";
    dn-events-extensions:event-snmp-trap-oid ".1.3.6.1.4.1.49739.2.8.0.4";
    dn-events-extensions:event-snmp-trap-vars "dnRsMemoryUtilThreshold.CONVERTIDX(memID,{node-type},{node-id},{mem-id}) {threshold} ; dnRsMemoryUtilization.CONVERTIDX(memID,{node-type},{node-id},{mem-id}) {utilization}";
    leaf node-type {
      type string;
      description
        "Node type";
    }
    leaf node-id {
      type uint16;
      description
        "Node ID";
    }
    leaf total-memory-value {
      type uint64;
      description
        "Total memory";
    }
    leaf memory-value {
      type uint64;
      description
        "Current memory usage";
    }
    leaf threshold {
      type uint16;
      description
        "Threshold in percent";
    }
    leaf utilization {
      type uint8;
      units "percent";
      description
        "Memory utilization rate in percent";
    }
    leaf mem-id {
      type uint16;
      description
        "Memory identification";
    }
  }

  notification PLATFORM_MEMORY_THRESHOLD_EXCEEDED {
    description
      "The memory in the node listed has crossed the threshold.";
    dn-events-extensions:event-severity-level "Warning";
    dn-events-extensions:event-message-string "Memory in {node-type} {node-id} is above the threshold ({threshold}%), current usage is {memory-value} MB , total available memory is {total-memory-value} MB";
    dn-events-extensions:event-corrective-action-string "No corrective action required.";
    dn-events-extensions:event-trigger-component-string "WB Agent";
    dn-events-extensions:event-group "Platform";
    dn-events-extensions:event-snmp-trap-name "dnRsMemThresholdExceeded";
    dn-events-extensions:event-snmp-trap-oid ".1.3.6.1.4.1.49739.2.8.0.3";
    dn-events-extensions:event-snmp-trap-vars "dnRsMemoryUtilThreshold.CONVERTIDX(memID,{node-type},{node-id},{mem-id}) {threshold} ; dnRsMemoryUtilization.CONVERTIDX(memID,{node-type},{node-id},{mem-id}) {utilization}";
    leaf node-type {
      type string;
      description
        "Node type";
    }
    leaf node-id {
      type uint16;
      description
        "Node ID";
    }
    leaf total-memory-value {
      type uint64;
      description
        "Total memory";
    }
    leaf memory-value {
      type uint64;
      description
        "Current memory usage";
    }
    leaf threshold {
      type uint16;
      description
        "Threshold in percent";
    }
    leaf utilization {
      type uint8;
      units "percent";
      description
        "Memory utilization rate in percent";
    }
    leaf mem-id {
      type uint16;
      description
        "Memory identification";
    }
  }

  notification PLATFORM_DISK_WRITE_BW_LIMIT_REACHED {
    description
      "The disk write bandwidth in the node listed has reached the maximum limit of 100%.";
    dn-events-extensions:event-severity-level "Error";
    dn-events-extensions:event-message-string "Disk write bandwidth in {node-type} {node-id} has reached the limit, read disk is {total-read-value} MB/s, write disk is {total-write-value} MB/s";
    dn-events-extensions:event-corrective-action-string "Clear redundant applications or files in use such as log files.";
    dn-events-extensions:event-trigger-component-string "Operational-infra";
    dn-events-extensions:event-group "Platform";
    leaf node-type {
      type string;
      description
        "Node type";
    }
    leaf node-id {
      type uint16;
      description
        "Node ID";
    }
    leaf total-read-value {
      type uint64;
      description
        "Total disk read/s";
    }
    leaf total-write-value {
      type uint64;
      description
        "Total disk write/s";
    }
  }

  notification PLATFORM_DISK_WRITE_BW_LIMIT_CLEARED {
    description
      "The disk write bandwidth in the node listed is below the threshold.";
    dn-events-extensions:event-severity-level "Info";
    dn-events-extensions:event-message-string "Disk write bandwidth in {node-type} {node-id} is below the threshold ({threshold}%), current disk read is {total-read-value} MB/s, current disk write is {total-write-value} MB/s";
    dn-events-extensions:event-corrective-action-string "This is informational, no corrective action required.";
    dn-events-extensions:event-trigger-component-string "Operational-infra";
    dn-events-extensions:event-group "Platform";
    leaf node-type {
      type string;
      description
        "Node type";
    }
    leaf node-id {
      type uint16;
      description
        "Node ID";
    }
    leaf total-read-value {
      type uint64;
      description
        "Total disk read/s";
    }
    leaf total-write-value {
      type uint64;
      description
        "Total disk write/s";
    }
    leaf threshold {
      type uint16;
      description
        "Threshold in percent";
    }
  }

  notification PLATFORM_DISK_WRITE_BW_THRESHOLD_EXCEEDED {
    description
      "The disk write bandwidth in the node listed has crossed the threshold.";
    dn-events-extensions:event-severity-level "Warning";
    dn-events-extensions:event-message-string "Disk write bandwidth in {node-type} {node-id} is above the threshold ({threshold}%), current read value is {total-read-value} MB/s, current write value is {total-write-value} MB/s";
    dn-events-extensions:event-corrective-action-string "No corrective action required.";
    dn-events-extensions:event-trigger-component-string "Operational-infra";
    dn-events-extensions:event-group "Platform";
    leaf node-type {
      type string;
      description
        "Node type";
    }
    leaf node-id {
      type uint16;
      description
        "Node ID";
    }
    leaf total-read-value {
      type uint64;
      description
        "Total disk read/s";
    }
    leaf total-write-value {
      type uint64;
      description
        "Total disk write/s";
    }
    leaf threshold {
      type uint16;
      description
        "Threshold in percent";
    }
  }

  notification PLATFORM_DISK_WRITE_BW_THRESHOLD_CLEARED {
    description
      "The disk write bandwidth in the node listed is below the threshold.";
    dn-events-extensions:event-severity-level "Info";
    dn-events-extensions:event-message-string "Disk write bandwidth in {node-type} {node-id} is below the threshold ({threshold}%), current read value is {total-read-value} MB/s, current write value is {total-write-value} MB/s";
    dn-events-extensions:event-corrective-action-string "This is informational, no corrective action required.";
    dn-events-extensions:event-trigger-component-string "Operational-infra";
    dn-events-extensions:event-group "Platform";
    leaf node-type {
      type string;
      description
        "Node type";
    }
    leaf node-id {
      type uint16;
      description
        "Node ID";
    }
    leaf total-read-value {
      type uint64;
      description
        "Total disk read/s";
    }
    leaf total-write-value {
      type uint64;
      description
        "Total disk write/s";
    }
    leaf threshold {
      type uint16;
      description
        "Threshold in percent";
    }
  }

  notification PLATFORM_CONTROL_TRAFFIC_THRESHOLD_EXCEEDED {
    description
      "Control network traffic is above the threshold.";
    dn-events-extensions:event-severity-level "Debug";
    dn-events-extensions:event-message-string "Control network traffic from and to {node-type} {node-id} is above the threshold ({threshold}Mb/s)";
    dn-events-extensions:event-corrective-action-string "No corrective action required.";
    dn-events-extensions:event-trigger-component-string "Operational-infra";
    dn-events-extensions:event-group "Platform";
    leaf node-type {
      type string;
      description
        "Node type";
    }
    leaf node-id {
      type uint16;
      description
        "Node ID";
    }
    leaf threshold {
      type uint16;
      description
        "Threshold in Mb/s";
    }
  }

  notification PLATFORM_CONTROL_TRAFFIC_THRESHOLD_CLEARED {
    description
      "Control network traffic is below the threshold.";
    dn-events-extensions:event-severity-level "Debug";
    dn-events-extensions:event-message-string "Control network traffic from and to {node-type} {node-id} is below the threshold ({threshold}Mb/s)";
    dn-events-extensions:event-corrective-action-string "This is informational, no corrective action required.";
    dn-events-extensions:event-trigger-component-string "Operational-infra";
    dn-events-extensions:event-group "Platform";
    leaf node-type {
      type string;
      description
        "Node type";
    }
    leaf node-id {
      type uint16;
      description
        "Node ID";
    }
    leaf threshold {
      type uint16;
      description
        "Threshold in Mb/s";
    }
  }

  notification PLATFORM_CONTROL_TRAFFIC_LIMIT_REACHED {
    description
      "Limit network traffic is above the threshold.";
    dn-events-extensions:event-severity-level "Debug";
    dn-events-extensions:event-message-string "Control network traffic from and to {node-type} {node-id} is above the threshold ({threshold}Mb/s)";
    dn-events-extensions:event-corrective-action-string "Investigate traffic in cluster.";
    dn-events-extensions:event-trigger-component-string "Operational-infra";
    dn-events-extensions:event-group "Platform";
    leaf node-type {
      type string;
      description
        "Node type";
    }
    leaf node-id {
      type uint16;
      description
        "Node ID";
    }
    leaf threshold {
      type uint16;
      description
        "Threshold in Mb/s";
    }
  }

  notification PLATFORM_CONTROL_TRAFFIC_LIMIT_CLEARED {
    description
      "Limit network traffic is below the threshold.";
    dn-events-extensions:event-severity-level "Debug";
    dn-events-extensions:event-message-string "Control network traffic from and to {node-type} {node-id} is below the threshold ({threshold}Mb/s)";
    dn-events-extensions:event-corrective-action-string "This is informational, no corrective action required.";
    dn-events-extensions:event-trigger-component-string "Operational-infra";
    dn-events-extensions:event-group "Platform";
    leaf node-type {
      type string;
      description
        "Node type";
    }
    leaf node-id {
      type uint16;
      description
        "Node ID";
    }
    leaf threshold {
      type uint16;
      description
        "Threshold in Mb/s";
    }
  }

  notification PLATFORM_MEMORY_CONSISTENT_CORRECTABLE_ERROR {
    description
      "The memory includes a consistent correctable error.";
    dn-events-extensions:event-severity-level "Error";
    dn-events-extensions:event-message-string "Memory in {node-type} {node-id} was detected with a consistent correctable bit on memory controller {mc-id}, channel {channel-id}, slot {slot-id}";
    dn-events-extensions:event-corrective-action-string "Replace memory DIMM on indicated channel and slot.";
    dn-events-extensions:event-trigger-component-string "Sys info";
    dn-events-extensions:event-group "Platform";
    leaf node-type {
      type string;
      description
        "Node type";
    }
    leaf node-id {
      type uint16;
      description
        "Node ID";
    }
    leaf mc-id {
      type uint16;
      description
        "Memory controller ID";
    }
    leaf channel-id {
      type uint16;
      description
        "Memory channel ID";
    }
    leaf slot-id {
      type uint16;
      description
        "Memory slot ID";
    }
  }

  notification PLATFORM_BASEOS_EVENT_DETECTED {
    description
      "A BaseOS kernel event has been detected. Check the message for severity, node, and kernel message.";
    dn-events-extensions:event-severity-level "Debug";
    dn-events-extensions:event-message-string "BaseOS kernel log message with severity {kernel-severity} captured on {node-type} {node-id}. Message: {log-entry}";
    dn-events-extensions:event-corrective-action-string "Check the log message field for more details.";
    dn-events-extensions:event-trigger-component-string "kernel";
    dn-events-extensions:event-group "Platform";
    leaf node-type {
      type string;
      description
        "Node type";
    }
    leaf node-id {
      type uint16;
      description
        "Node ID";
    }
    leaf kernel-severity {
      type string;
      description
        "BaseOS kernel log message severity level (emerg, alert etc.)";
    }
    leaf log-entry {
      type string;
      description
        "BaseOS kernel log message";
    }
  }

  notification OOM_KILLER_PROCESS {
    description
      "The Kernel is out of memory and stopped the process indicated in the message text.";
    dn-events-extensions:event-severity-level "Warning";
    dn-events-extensions:event-message-string "Process name {proc-name} with pid {proc-id} was killed.";
    dn-events-extensions:event-corrective-action-string "No corrective action required.";
    dn-events-extensions:event-trigger-component-string "kernel";
    dn-events-extensions:event-group "Platform";
    leaf proc-name {
      type string;
      description
        "Process name";
    }
    leaf proc-id {
      type uint32;
      description
        "Process identification";
    }
  }

  ///****** Routing Protocols Events *****///
  // ISIS events

  notification ISIS_NEIGHBOR_ADJACENCY_UP {
    description
      "The ISIS neighbor adjacency has moved to an 'up' state.";
    dn-events-extensions:event-severity-level "Info";
    dn-events-extensions:event-message-string "ISIS instance {instance} neighbor {neighbor-system-id} level {level} adjacency moved to an UP state, on interface {if-name}";
    dn-events-extensions:event-corrective-action-string "This is informational, no corrective action required.";
    dn-events-extensions:event-trigger-component-string "ISIS";
    dn-events-extensions:event-group "ISIS";
    dn-events-extensions:event-snmp-trap-name "isisAdjacencyChange";
    dn-events-extensions:event-snmp-trap-oid "1.3.6.1.2.1.138.0.17";
    dn-events-extensions:event-snmp-trap-vars "isisNotificationSysLevelIndex.0 {level} ; isisNotificationCircIfIndex.0 {if-index} ; isisPduLspId.0 {link-state-pdu-id} ; isisAdjState.0 {state}";
    leaf instance {
      type string;
      description
        "ISIS instance name";
    }
    leaf neighbor-system-id {
      type string;
      description
        "Neighbor system ID";
    }
    leaf if-name {
      type string;
      description
        "Interface name";
    }
    leaf if-index {
      type uint32 {
        range "1..2147483647";
      }
      description
        "The identifier of this circuit (interface) relevant to
         this notification";
    }
    leaf level {
      type enumeration {
        enum level1 {
          value 1;
        }
        enum level2 {
          value 2;
        }
        enum level1and2 {
          value 3;
        }
      }
      description
        "The system level for this notification";
    }
    leaf link-state-pdu-id {
      type binary {
        length "8";
      }
      description
        "A Binary String that uniquely identifies
         a Link State PDU.
         SNMP: The 8-byte Link State PDU (LSP) ID,
         consisting of the 6-byte SystemID of the
         originating IS; a one-byte PseudoNode ID,
         which is 0 unless the LSP represents the
         topology of a LAN; and a one-byte LSP
         fragment number that is issued in sequence,
         starting with 0.  Non-zero PseudoNode IDs
         need to be unique to the IS but need not
         match the IfIndex.";
    }
    leaf state {
      type enumeration {
        enum up {
          value 3;
        }
      }
      description
        "The current state of an adjacency. Expected to be up(3)";
    }
  }

  notification ISIS_NEIGHBOR_ADJACENCY_DOWN {
    description
      "ISIS neighbor adjacency moved from 'up' state to a 'down' or 'init' state. This is because of either a network error to the neighbor or the neighbor stopped responding.";
    dn-events-extensions:event-severity-level "Warning";
    dn-events-extensions:event-message-string "ISIS instance {instance} neighbor {neighbor-system-id} level {level} adjacency moved to a {state} state, on interface {if-name}";
    dn-events-extensions:event-corrective-action-string "No corrective action.";
    dn-events-extensions:event-trigger-component-string "ISIS";
    dn-events-extensions:event-group "ISIS";
    dn-events-extensions:event-snmp-trap-name "isisAdjacencyChange";
    dn-events-extensions:event-snmp-trap-oid "1.3.6.1.2.1.138.0.17";
    dn-events-extensions:event-snmp-trap-vars "isisNotificationSysLevelIndex.0 {level} ; isisNotificationCircIfIndex.0 {if-index} ; isisPduLspId.0 {link-state-pdu-id} ; isisAdjState.0 {state}";
    leaf instance {
      type string;
      description
        "ISIS instance name";
    }
    leaf neighbor-system-id {
      type string;
      description
        "Neighbor system ID";
    }
    leaf if-name {
      type string;
      description
        "Interface name";
    }
    leaf if-index {
      type uint32 {
        range "1..2147483647";
      }
      description
        "The identifier of this circuit (interface) relevant to
         this notification";
    }
    leaf level {
      type enumeration {
        enum level1 {
          value 1;
        }
        enum level2 {
          value 2;
        }
        enum level1and2 {
          value 3;
        }
      }
      description
        "The system level for this notification";
    }
    leaf link-state-pdu-id {
      type binary {
        length "8";
      }
      description
        "A Binary String that uniquely identifies
         a Link State PDU.
         SNMP: The 8-byte Link State PDU (LSP) ID,
         consisting of the 6-byte SystemID of the
         originating IS; a one-byte PseudoNode ID,
         which is 0 unless the LSP represents the
         topology of a LAN; and a one-byte LSP
         fragment number that is issued in sequence,
         starting with 0.  Non-zero PseudoNode IDs
         need to be unique to the IS but need not
         match the IfIndex.";
    }
    leaf state {
      type enumeration {
        enum down {
          value 1;
        }
        enum initializing {
          value 2;
        }
        enum failed {
          value 4;
        }
      }
      description
        "The current state of an adjacency. Expected to be not up(4)";
    }
  }

  notification ISIS_NEIGHBOR_ADJACENCY_REJECTED {
    description
      "The ISIS neighbor adjacency was rejected due to an invalid hello packet.";
    dn-events-extensions:event-severity-level "Notice";
    dn-events-extensions:event-message-string "ISIS instance {instance} neighbor {neighbor-system-id} level {level} on interface {if-name} adjacency was rejected due to an invalid hello";
    dn-events-extensions:event-corrective-action-string "No corrective action.";
    dn-events-extensions:event-trigger-component-string "ISIS";
    dn-events-extensions:event-group "ISIS";
    dn-events-extensions:event-snmp-trap-name "isisRejectedAdjacency";
    dn-events-extensions:event-snmp-trap-oid "1.3.6.1.2.1.138.0.13";
    dn-events-extensions:event-snmp-trap-vars "isisNotificationSysLevelIndex.0 {level} ; isisNotificationCircIfIndex.0 {if-index} ; isisPduFragment.0 {pdu-fragment} ";
    leaf instance {
      type string;
      description
        "ISIS instance name";
    }
    leaf neighbor-system-id {
      type string;
      description
        "Neighbor system ID";
    }
    leaf if-name {
      type string;
      description
        "Interface name";
    }
    leaf if-index {
      type uint32 {
        range "1..2147483647";
      }
      description
        "The identifier of this circuit (interface) relevant to
         this notification";
    }
    leaf level {
      type enumeration {
        enum level1 {
          value 1;
        }
        enum level2 {
          value 2;
        }
        enum level1and2 {
          value 3;
        }
      }
      description
        "The system level for this notification";
    }
    leaf pdu-fragment {
      type binary {
        length "1..64";
      }
      description
        "SNMP: Holds up to 64 initial bytes of a PDU that
         triggered the notification";
    }
  }

  notification ISIS_LSP_CHECKSUM_FAILED {
    description
      "The ISIS LSP packet checksum validates whether the packet has become corrupt. The packet failed validation due to the packet being corrupt and has been has dropped.";
    dn-events-extensions:event-severity-level "Warning";
    dn-events-extensions:event-message-string "ISIS instance {instance} level {level} received LSP packet on interface {if-name}. Packet failed checksum validation";
    dn-events-extensions:event-corrective-action-string "No corrective action.";
    dn-events-extensions:event-trigger-component-string "ISIS";
    dn-events-extensions:event-group "ISIS";
    leaf instance {
      type string;
      description
        "ISIS instance name";
    }
    leaf level {
      type string;
      description
        "ISIS level";
    }
    leaf if-name {
      type string;
      description
        "Interface name";
    }
  }

  notification ISIS_AUTHENTICATION_FAILED {
    description
      "ISIS failed to validate the LSP/SNP/HELLO packet received, the packet was dropped.";
    dn-events-extensions:event-severity-level "Warning";
    dn-events-extensions:event-message-string "ISIS instance {instance} received {level} {pdu} with system ID {system-id} on interface {if-name}. {pdu} authentication failed. Packet was dropped.";
    dn-events-extensions:event-corrective-action-string "Check that the password configuration is the same on both the local and remote system.";
    dn-events-extensions:event-trigger-component-string "ISIS";
    dn-events-extensions:event-group "ISIS";
    dn-events-extensions:event-snmp-trap-name "isisAuthenticationFailure";
    dn-events-extensions:event-snmp-trap-oid "1.3.6.1.2.1.138.0.10";
    dn-events-extensions:event-snmp-trap-vars "isisNotificationSysLevelIndex.0 {level} ; isisNotificationCircIfIndex.0 {if-index} ; isisPduFragment.0 {pdu-fragment} ";
    leaf instance {
      type string;
      description
        "ISIS instance name";
    }
    leaf pdu {
      type enumeration {
        enum LSP;
        enum CSNP;
        enum PSNP;
        enum HELLO;
      }
      description
        "ISIS packet type";
    }
    leaf if-name {
      type string;
      description
        "Interface name";
    }
    leaf system-id {
      description
        "ISIS neighbor system ID";
      type string;
    }
    leaf if-index {
      type uint32 {
        range "1..2147483647";
      }
      description
        "The identifier of this circuit (interface) relevant to
         this notification";
    }
    leaf level {
      type enumeration {
        enum level1 {
          value 1;
        }
        enum level2 {
          value 2;
        }
        enum level1and2 {
          value 3;
        }
      }
      description
        "The system level for this notification";
    }
    leaf pdu-fragment {
      type binary {
        length "1..64";
      }
      description
        "SNMP: Holds up to 64 initial bytes of a PDU that
         triggered the notification";
    }
  }

  notification ISIS_AUTHENTICATION_TYPE_FAILED {
    description
      "ISIS received a PDU with an authentication type that does not match the local authentication settings, the packet was dropped.";
    dn-events-extensions:event-severity-level "Warning";
    dn-events-extensions:event-message-string "ISIS instance {instance} level {level} received {pdu} on interface {if-name}. {pdu} authentication type does not match authentication settings. Packet was dropped";
    dn-events-extensions:event-corrective-action-string "No corrective action.";
    dn-events-extensions:event-trigger-component-string "ISIS";
    dn-events-extensions:event-group "ISIS";
    dn-events-extensions:event-snmp-trap-name "isisAuthenticationTypeFailure";
    dn-events-extensions:event-snmp-trap-oid "1.3.6.1.2.1.138.0.9";
    dn-events-extensions:event-snmp-trap-vars "isisNotificationSysLevelIndex.0 {level} ; isisNotificationCircIfIndex.0 {if-index} ; isisPduFragment.0 {pdu-fragment} ";
    leaf instance {
      type string;
      description
        "ISIS instance name";
    }
    leaf if-name {
      type string;
      description
        "Interface name";
    }
    leaf pdu {
      description
        "ISIS packet types";
      type enumeration {
        enum LSP;
        enum CSNP;
        enum PSNP;
        enum HELLO;
      }
    }
    leaf if-index {
      type uint32 {
        range "1..2147483647";
      }
      description
        "The identifier of this circuit (interface) relevant to
         this notification";
    }
    leaf level {
      type enumeration {
        enum level1 {
          value 1;
        }
        enum level2 {
          value 2;
        }
        enum level1and2 {
          value 3;
        }
      }
      description
        "The system level for this notification";
    }
    leaf pdu-fragment {
      type binary {
        length "1..64";
      }
      description
        "SNMP: Holds up to 64 initial bytes of a PDU that
         triggered the notification";
    }
  }

  notification ISIS_OVERLOAD_BIT_ON {
    description
      "ISIS has set the overload bit to 'on'. This means other routers will not include the router in SPF path calculation and will not route traffic through the router.";
    dn-events-extensions:event-severity-level "Notice";
    dn-events-extensions:event-message-string "ISIS instance {instance} level {level} overload-bit was set to on, period: {period}";
    dn-events-extensions:event-corrective-action-string "No corrective action.";
    dn-events-extensions:event-trigger-component-string "ISIS";
    dn-events-extensions:event-group "ISIS";
    dn-events-extensions:event-snmp-trap-name "isisDatabaseOverload";
    dn-events-extensions:event-snmp-trap-oid "1.3.6.1.2.1.138.0.1";
    dn-events-extensions:event-snmp-trap-vars "isisNotificationSysLevelIndex.0 {level} ; isisSysLevelState.0 {system-level} ";
    leaf instance {
      type string;
      description
        "ISIS instance name";
    }
    leaf level {
      type enumeration {
        enum level1 {
          value 1;
        }
        enum level2 {
          value 2;
        }
        enum level1and2 {
          value 3;
        }
      }
      description
        "The system level for this notification";
    }
    leaf system-level {
      type enumeration {
        enum off {
          value 1;
        }
        enum on {
          value 2;
        }
        enum waiting {
          value 3;
        }
        enum overloaded {
          value 4;
        }
      }
      description
        "SNMP: The state of the database at this level.
         The value 'off' indicates that IS-IS is not active at
         this level.
         The value 'on' indicates that IS-IS is active at this
         level and is not overloaded.
         The value 'waiting' indicates a database that is low on
         an essential resource, such as memory.
         The administrator may force the state to 'overloaded'
         by setting the object isisSysLevelSetOverload.
         If the state is 'waiting' or 'overloaded', we
         originate LSPs with the overload bit set";
    }
    leaf period {
      type string;
      description
        "The period for which OL-bit is set";
    }
  }

  notification ISIS_OVERLOAD_BIT_OFF {
    description
      "ISIS has set the overload bit to 'off'. This means other routers can route traffic through the router.";
    dn-events-extensions:event-severity-level "Info";
    dn-events-extensions:event-message-string "ISIS instance {instance} level {level} overload-bit was set to off";
    dn-events-extensions:event-corrective-action-string "This is informational, no corrective action required.";
    dn-events-extensions:event-trigger-component-string "ISIS";
    dn-events-extensions:event-group "ISIS";
    dn-events-extensions:event-snmp-trap-name "isisDatabaseOverload";
    dn-events-extensions:event-snmp-trap-oid "1.3.6.1.2.1.138.0.1";
    dn-events-extensions:event-snmp-trap-vars "isisNotificationSysLevelIndex.0 {level} ; isisSysLevelState.0 {system-level} ";
    leaf instance {
      type string;
      description
        "ISIS instance name";
    }
    leaf level {
      type enumeration {
        enum level1 {
          value 1;
        }
        enum level2 {
          value 2;
        }
        enum level1and2 {
          value 3;
        }
      }
      description
        "The system level for this notification";
    }
    leaf system-level {
      type enumeration {
        enum off {
          value 1;
        }
        enum on {
          value 2;
        }
        enum waiting {
          value 3;
        }
        enum overloaded {
          value 4;
        }
      }
      description
        "SNMP: The state of the database at this level.
         The value 'off' indicates that IS-IS is not active at
         this level.
         The value 'on' indicates that IS-IS is active at this
         level and is not overloaded.
         The value 'waiting' indicates a database that is low on
         an essential resource, such as memory.
         The administrator may force the state to 'overloaded'
         by setting the object isisSysLevelSetOverload.
         If the state is 'waiting' or 'overloaded', we
         originate LSPs with the overload bit set";
    }
  }

  notification ISIS_ADVERTISE_MAX_METRIC_ON {
    description
      "ISIS has set the max metric on all interfaces. This means other routers will consider the router to be least preferred in SPF path calculation.";
    dn-events-extensions:event-severity-level "Notice";
    dn-events-extensions:event-message-string "ISIS instance {instance} level {level} advertise max-metric was set to on, period: {period}";
    dn-events-extensions:event-corrective-action-string "No corrective action.";
    dn-events-extensions:event-trigger-component-string "isis";
    dn-events-extensions:event-group "ISIS";
    leaf instance {
      type string;
      description
        "ISIS instance name";
    }
    leaf level {
      type enumeration {
        enum level1 {
          value 1;
        }
        enum level2 {
          value 2;
        }
        enum level1and2 {
          value 3;
        }
      }
      description
        "The system level for this notification";
    }
    leaf period {
      type string;
      description
        "The period for which max-metric is set";
    }
  }

  notification ISIS_ADVERTISE_MAX_METRIC_OFF {
    description
      "ISIS has turned off the max metric on all interfaces.";
    dn-events-extensions:event-severity-level "Info";
    dn-events-extensions:event-message-string "ISIS instance {instance} level {level} advertise max-metric was set to off";
    dn-events-extensions:event-corrective-action-string "No corrective action.";
    dn-events-extensions:event-trigger-component-string "isis";
    dn-events-extensions:event-group "ISIS";
    leaf instance {
      type string;
      description
        "ISIS instance name";
    }
    leaf level {
      type enumeration {
        enum level1 {
          value 1;
        }
        enum level2 {
          value 2;
        }
        enum level1and2 {
          value 3;
        }
      }
      description
        "The system level for this notification";
    }
  }

  notification ISIS_DUPLICATE_SYSTEM_ID {
    description
      "ISIS has detected a remote node with a duplicate system-id that is the same as the local system-id.";
    dn-events-extensions:event-severity-level "Warning";
    dn-events-extensions:event-message-string "ISIS instance {instance} level {level} has detected a possible remote system with a duplicate system-id that is the same as the local system-id. System-id {system-id}. Local system info: hostname {local-hostname}, fingerprint {local-fingerprint}. Received LSP info: hostname {remote-hostname}, fingerprint {remote-fingerprint}";
    dn-events-extensions:event-corrective-action-string "Update the configured system-id in either system.";
    dn-events-extensions:event-trigger-component-string "ISIS";
    dn-events-extensions:event-group "ISIS";
    leaf instance {
      type string;
      description
        "ISIS instance name";
    }
    leaf level {
      type enumeration {
        enum level1 {
          value 1;
        }
        enum level2 {
          value 2;
        }
      }
      description
        "The system level for this notification";
    }
    leaf system-id {
      type string;
      description
        "ISIS system-id. 6byte in format ssss.ssss.ssss ";
    }
    leaf local-hostname {
      type string;
      description
        "Local IS-IS hostname, 'N/A' if unknown";
    }
    leaf local-fingerprint {
      type string;
      description
        "Local IS-IS fingerprint per RFC8196, 'N/A' if unknown";
    }
    leaf remote-hostname {
      type string;
      description
        "Remote IS-IS hostname, 'N/A' if unknown";
    }
    leaf remote-fingerprint {
      type string;
      description
        "Remote IS-IS fingerprint per RFC8196, 'N/A' if unknown";
    }
  }

  notification ISIS_PURGE_EVENT {
    description
      "ISIS received an LSP purge.";
    dn-events-extensions:event-severity-level "Debug";
    dn-events-extensions:event-message-string "ISIS instance {instance} level {level} detected purge event for LSP {lsp-id} Sequence {lsp-seq} . Purge Originator Identification: {poi}";
    dn-events-extensions:event-corrective-action-string "No corrective action.";
    dn-events-extensions:event-trigger-component-string "ISIS";
    dn-events-extensions:event-group "ISIS";
    leaf instance {
      type string;
      description
        "ISIS instance name";
    }
    leaf level {
      type enumeration {
        enum level1 {
          value 1;
        }
        enum level2 {
          value 2;
        }
      }
      description
        "ISIS level";
    }
    leaf lsp-id {
      type string;
      description
        "The LSP identification";
    }
    leaf lsp-seq {
      type string;
      description
        "The LSP sequence number";
    }
    leaf poi {
      type string;
      description
        "The Purge Originator Identification information";
    }
  }

  notification ISIS_MAXIMUM_INSTANCES_LIMIT_REACHED {
    description
      "The number of ISIS instances has reached the configured system limit.";
    dn-events-extensions:event-severity-level "Notice";
    dn-events-extensions:event-message-string "Number of ISIS instances has reached system limit of {limit}";
    dn-events-extensions:event-corrective-action-string "To configure a new ISIS instance, an existing instance must be removed.";
    dn-events-extensions:event-trigger-component-string "ISIS";
    dn-events-extensions:event-group "ISIS";
    leaf limit {
      description
        "Session number limit";
      type enumeration {
        enum 5;
      }
    }
  }

  notification ISIS_MAXIMUM_INSTANCES_LIMIT_CLEARED {
    description
      "The number of ISIS instances is below the system limit.";
    dn-events-extensions:event-severity-level "Info";
    dn-events-extensions:event-message-string "Number of ISIS instances is below the system limit of {limit}";
    dn-events-extensions:event-corrective-action-string "This is informational, no corrective action required.";
    dn-events-extensions:event-trigger-component-string "ISIS";
    dn-events-extensions:event-group "ISIS";
    leaf limit {
      description
        "Session number limit";
      type enumeration {
        enum 5;
      }
    }
  }

  notification ISIS_MAXIMUM_ADJACENCIES_LIMIT_REACHED {
    description
      "The number of ISIS adjacencies has reached the configured system limit.";
    dn-events-extensions:event-severity-level "Warning";
    dn-events-extensions:event-message-string "Number of ISIS adjacencies has reached system limit of {limit}";
    dn-events-extensions:event-corrective-action-string "No corrective action.";
    dn-events-extensions:event-trigger-component-string "ISIS";
    dn-events-extensions:event-group "ISIS";
    leaf limit {
      type uint16;
      description
        "The accumulated adjacencies scale on all instances";
    }
  }

  notification ISIS_MAXIMUM_ADJACENCIES_LIMIT_CLEARED {
    description
      "ISIS adjacencies have been removed, the number of ISIS adjacencies is below the system limit.";
    dn-events-extensions:event-severity-level "Info";
    dn-events-extensions:event-message-string "Number of ISIS adjacencies is below the system limit of {limit} adjacencies";
    dn-events-extensions:event-corrective-action-string "This is informational, no corrective action required.";
    dn-events-extensions:event-trigger-component-string "ISIS";
    dn-events-extensions:event-group "ISIS";
    leaf limit {
      type uint16;
      description
        "The accumulated adjacencies scale on all instances";
    }
  }

  notification ISIS_MAXIMUM_ADJACENCIES_THRESHOLD_EXCEEDED {
    description
      "The number of ISIS adjacencies has crossed the system threshold.";
    dn-events-extensions:event-severity-level "Notice";
    dn-events-extensions:event-message-string "Number of ISIS adjacencies has crossed the system threshold {threshold}% limit of {limit}, the number of ISIS adjacencies are ({numeric-value})";
    dn-events-extensions:event-corrective-action-string "No corrective action.";
    dn-events-extensions:event-trigger-component-string "ISIS";
    dn-events-extensions:event-group "ISIS";
    leaf threshold {
      type uint8;
      description
        "Threshold percent";
    }
    leaf numeric-value {
      type uint16;
      description
        "Current number of ISIS adjacencies";
    }
    leaf limit {
      type uint16;
      description
        "The accumulated adjacencies scale on all instances";
    }
  }

  notification ISIS_MAXIMUM_ADJACENCIES_THRESHOLD_CLEARED {
    description
      "The number of ISIS adjacencies is below the system threshold.";
    dn-events-extensions:event-severity-level "Info";
    dn-events-extensions:event-message-string "Number of ISIS adjacencies is below the system threshold {threshold}% of the limit ({limit}), the current number of ISIS adjacencies are ({numeric-value})";
    dn-events-extensions:event-corrective-action-string "This is informational, no corrective action required.";
    dn-events-extensions:event-trigger-component-string "ISIS";
    dn-events-extensions:event-group "ISIS";
    leaf threshold {
      type uint8;
      description
        "Threshold percent";
    }
    leaf numeric-value {
      type uint16;
      description
        "Current number of ISIS adjacencies";
    }
    leaf limit {
      type uint16;
      description
        "The accumulated adjacencies scale on all instances";
    }
  }

  notification ISIS_MAXIMUM_ROUTES_LIMIT_REACHED {
    description
      "The number of ISIS routes has reached the system limit.";
    dn-events-extensions:event-severity-level "Warning";
    dn-events-extensions:event-message-string "Number of ISIS routes has reached the system limit of {limit} routes";
    dn-events-extensions:event-corrective-action-string "No corrective action.";
    dn-events-extensions:event-trigger-component-string "ISIS";
    dn-events-extensions:event-group "ISIS";
    leaf limit {
      type uint16;
      description
        "The accumulated routes scale on all instances and address-families";
    }
  }

  notification ISIS_MAXIMUM_ROUTES_LIMIT_CLEARED {
    description
      "Routes have been removed, the number of ISIS routes is below the system limit.";
    dn-events-extensions:event-severity-level "Info";
    dn-events-extensions:event-message-string "Number of routes is below the system limit of {limit} routes";
    dn-events-extensions:event-corrective-action-string "This is informational, no corrective action required.";
    dn-events-extensions:event-trigger-component-string "ISIS";
    dn-events-extensions:event-group "ISIS";
    leaf limit {
      type uint16;
      description
        "The accumulated routes scale on all instances and address-families";
    }
  }

  notification ISIS_MAXIMUM_ROUTES_THRESHOLD_EXCEEDED {
    description
      "The number of ISIS routes has crossed the system threshold.";
    dn-events-extensions:event-severity-level "Notice";
    dn-events-extensions:event-message-string "Number of ISIS routes has crossed the system threshold {threshold}% of the limit ({limit}), the current number of routes are ({numeric-value})";
    dn-events-extensions:event-corrective-action-string "No corrective action.";
    dn-events-extensions:event-trigger-component-string "ISIS";
    dn-events-extensions:event-group "ISIS";
    leaf threshold {
      type uint8;
      description
        "Threshold percent";
    }
    leaf numeric-value {
      type uint16;
      description
        "Current number of ISIS routes";
    }
    leaf limit {
      type uint16;
      description
        "The accumulated routes scale on all instances and address-families";
    }
  }

  notification ISIS_MAXIMUM_ROUTES_THRESHOLD_CLEARED {
    description
      "The number of ISIS routes is below the system threshold.";
    dn-events-extensions:event-severity-level "Info";
    dn-events-extensions:event-message-string "Number of routes is below the system threshold {threshold}% of the limit ({limit}), the current number of routes are ({numeric-value})";
    dn-events-extensions:event-corrective-action-string "This is informational, no corrective action required.";
    dn-events-extensions:event-trigger-component-string "ISIS";
    dn-events-extensions:event-group "ISIS";
    leaf threshold {
      type uint8;
      description
        "Threshold percent";
    }
    leaf numeric-value {
      type uint16;
      description
        "Current number of ISIS routes";
    }
    leaf limit {
      type uint16;
      description
        "The accumulated routes scale on all instances and address-families";
    }
  }

  // ISIS nsr events

  notification ISIS_NSR_RECOVERED {
    description
      "The system performed an IS-IS Non-Stop Routing recovery due to a restart of the isisd process.";
    dn-events-extensions:event-severity-level "Notice";
    dn-events-extensions:event-message-string "IS-IS Non-Stop Routing recovery was performed due to a restart of the isisd process";
    dn-events-extensions:event-corrective-action-string "This is informational, no corrective action required.";
    dn-events-extensions:event-trigger-component-string "ISIS";
    dn-events-extensions:event-group "ISIS";
  }

  notification ISIS_NSR_RECOVERY_FAILED {
    description
      "The IS-IS process failed to recover in Non-Stop Routing mode.";
    dn-events-extensions:event-severity-level "Warning";
    dn-events-extensions:event-message-string "isisd process failed to recover in Non-Stop Routing mode";
    dn-events-extensions:event-corrective-action-string "Verify NSR readiness prior to the failure event. If the database was synchronized prior to the failure event, contact Customer Support.";
    dn-events-extensions:event-trigger-component-string "ISIS";
    dn-events-extensions:event-group "ISIS";
  }

  // Segment Routing events
  // IS-IS

  notification ISIS_SR_CONFIG_PREFIX_SID_OUT_OF_RANGE {
    description
      "The configured Prefix-SID is out of the currently in use SRGB range.";
    dn-events-extensions:event-severity-level "Warning";
    dn-events-extensions:event-message-string "Configured Prefix-SID value {sid-value} on {if-name}, is outside the currently in use SRGB range";
    dn-events-extensions:event-corrective-action-string "Update the Prefix-SID configuration or restart the router to add the new SRGB values.";
    dn-events-extensions:event-trigger-component-string "ISIS";
    dn-events-extensions:event-group "ISIS";
    leaf sid-value {
      type uint32;
      description
        "Absolute value of the Prefix-SID";
    }
    leaf if-name {
      type string;
      description
        "Interface name on which Prefix-SID was configured";
    }
    leaf sid-index {
      type int32;
      description
        "Index value of the Prefix-SID";
    }
  }

  notification ISIS_SR_CONFIG_BINDING_SID_OUT_OF_RANGE {
    description
      "The configured Binding-SID is out of the currently in use SRLB range.";
    dn-events-extensions:event-severity-level "Warning";
    dn-events-extensions:event-message-string "Configured SR-TE policy {policy-name} Binding-SID value {sid-value}, is outside the currently in use SRLB range";
    dn-events-extensions:event-corrective-action-string "Update the Binding-SID configuration or restart the router to add the new SRLB values.";
    dn-events-extensions:event-trigger-component-string "ISIS";
    dn-events-extensions:event-group "ISIS";
    leaf policy-name {
      type string;
      description
        "SR-TE policy name";
    }
    leaf sid-value {
      type uint32;
      description
        "Absolute value of the Prefix-SID";
    }
  }

  notification ISIS_SR_CONFIG_ADJ_SID_OUT_OF_RANGE {
    description
      "The configured Adjacency-SID is out of the currently in use SRLB range.";
    dn-events-extensions:event-severity-level "Warning";
    dn-events-extensions:event-message-string "Configured Adjacency-SID value {sid-value} on {if-name}, is outside the currently in use SRLB range";
    dn-events-extensions:event-corrective-action-string "Update the Adjacency-SID configuration or restart the router to add the new SRLB values.";
    dn-events-extensions:event-trigger-component-string "ISIS";
    dn-events-extensions:event-group "ISIS";
    leaf sid-value {
      type uint32;
      description
        "Absolute label value of the Prefix-SID";
    }
    leaf if-name {
      type string;
      description
        "Interface name on which Prefix-SID was configured";
    }
  }

  notification ISIS_SR_RECEIVED_PREFIX_SID_OUT_OF_RANGE {
    description
      "A Prefix-SID was received which is outside of the ISIS SRGB range.";
    dn-events-extensions:event-severity-level "Warning";
    dn-events-extensions:event-message-string "Received {sid-type} {sid-value} from {remote-hostname}. {sid-type} is outside the SRGB range";
    dn-events-extensions:event-corrective-action-string "Align the network SID requirements with the SRGB values.";
    dn-events-extensions:event-trigger-component-string "ISIS";
    dn-events-extensions:event-group "ISIS";
    leaf sid-type {
      type string;
      description
        "The received SID-type, either Prefix-SID or Binding-SID";
    }
    leaf sid-value {
      type uint32;
      description
        "Absolute value of the Prefix-SID";
    }
    leaf remote-hostname {
      type string;
      description
        "The hostname of removed node from which SID was received, if not known, display system-ID";
    }
  }

  notification ISIS_SR_PREFIX_SID_CONFLICT {
    description
      "A Prefix-SID was received which is the same for different Forwarding Equivalence Classes (FEC)s.";
    dn-events-extensions:event-severity-level "Warning";
    dn-events-extensions:event-message-string "Prefix-SID {sid-value} originated by {hostname-1} for {prefix-1} {algorithm-1} conflicts with Prefix-SID originated by {hostname-2} {algorithm-2} for {prefix-2}. Conflict resolved as {resolution}";
    dn-events-extensions:event-corrective-action-string "Change the Prefix-SID setting on either nodes.";
    dn-events-extensions:event-trigger-component-string "ISIS";
    dn-events-extensions:event-group "ISIS";
    leaf sid-value {
      type uint32;
      description
        "Absolute value of the Prefix-SID";
    }
    leaf hostname-1 {
      type string;
      description
        "The hostname of removed node from which SID was received, if not known, display system-ID";
    }
    leaf prefix-1 {
      type string;
      description
        "The prefix for which node-1 advertise the Prefix-SID";
    }
    leaf algorithm-1 {
      description
        "The prefix-SID algorithm, SPF or S-SFP";
      type string;
    }
    leaf hostname-2 {
      type string;
      description
        "The hostname of removed node from which SID was received, if not known, display system-ID";
    }
    leaf prefix-2 {
      type string;
      description
        "The prefix for which node-1 advertise the Prefix-SID";
    }
    leaf algorithm-2 {
      description
        "The prefix-SID algorithm, SPF or S-SFP";
      type string;
    }
    leaf resolution {
      type string;
      description
        "how conflict is resolved, i.e which prefix is assigned to sid";
    }
  }

  notification ISIS_SR_PREFIX_CONFLICT {
    description
      "Different Prefix-SIDs were received for the same Forwarding Equivalence Classes (FEC)s.";
    dn-events-extensions:event-severity-level "Warning";
    dn-events-extensions:event-message-string "ISIS {level} Prefix {ipv4-prefix} originated by {hostname-1} with Prefix-SID {sid-value-1} conflicts with Prefix-SID {sid-value-2} originated by {hostname-2}. Conflict resolved as {resolution}";
    dn-events-extensions:event-corrective-action-string "Change the Prefix-SID setting on either nodes.";
    dn-events-extensions:event-trigger-component-string "ISIS";
    dn-events-extensions:event-group "ISIS";
    leaf level {
      type enumeration {
        enum level1 {
          value 1;
        }
        enum level2 {
          value 2;
        }
      }
      description
        "The ISIS prefix level";
    }
    leaf ipv4-prefix {
      type string;
      description
        "The prefix received from multiple nodes";
    }
    leaf hostname-1 {
      type string;
      description
        "The hostname of removed node from which SID was received, if not known, display system-ID";
    }
    leaf sid-value-1 {
      type uint32;
      description
        "Absolute value of the Prefix-SID";
    }
    leaf sid-value-2 {
      type uint32;
      description
        "Absolute value of the Prefix-SID";
    }
    leaf hostname-2 {
      type string;
      description
        "The hostname of removed node from which SID was received, if not known, display system-ID";
    }
    leaf resolution {
      type string;
      description
        "how conflict is resolved, i.e which prefix-sid is assigned to prefix";
    }
  }

  // OSPF

  notification OSPF_SR_CONFIG_PREFIX_SID_OUT_OF_RANGE {
    description
      "The configured Prefix-SID is out of the currently in use SRGB range.";
    dn-events-extensions:event-severity-level "Warning";
    dn-events-extensions:event-message-string "OSPF instance {instance}: Configured Prefix-SID value {sid-value} on {if-name}, is outside the currently in use SRGB range";
    dn-events-extensions:event-corrective-action-string "Update the Prefix-SID configuration or restart the router to add the new SRGB values.";
    dn-events-extensions:event-trigger-component-string "OSPF";
    dn-events-extensions:event-group "OSPF";
    leaf instance {
      type string;
      description
        "OSPF instance name";
    }
    leaf sid-value {
      type uint32;
      description
        "Absolute value of the Prefix-SID";
    }
    leaf if-name {
      type string;
      description
        "Interface name on which Prefix-SID was configured";
    }
    leaf sid-index {
      type int32;
      description
        "Index value of the Prefix-SID";
    }
  }

  notification OSPF_SR_RECEIVED_PREFIX_SID_OUT_OF_RANGE {
    description
      "A Prefix-SID was received which is outside of the OSPF SRGB range.";
    dn-events-extensions:event-severity-level "Warning";
    dn-events-extensions:event-message-string "OSPF instance {instance}: Received {sid-type} {sid-value} from {remote-hostname}. {sid-type} is outside the SRGB range";
    dn-events-extensions:event-corrective-action-string "Align the network SID requirements with the SRGB values.";
    dn-events-extensions:event-trigger-component-string "OSPF";
    dn-events-extensions:event-group "OSPF";
    leaf instance {
      type string;
      description
        "OSPF instance name";
    }
    leaf sid-type {
      type string;
      description
        "The received SID-type, either Prefix-SID or Binding-SID";
    }
    leaf sid-value {
      type uint32;
      description
        "Absolute value of the Prefix-SID";
    }
    leaf remote-hostname {
      type string;
      description
        "The hostname of removed node from which SID was received, if not known, display system-ID";
    }
  }

  notification OSPF_SR_PREFIX_SID_CONFLICT {
    description
      "A Prefix-SID was received which is the same for different Forwarding Equivalence Classes (FEC)s.";
    dn-events-extensions:event-severity-level "Warning";
    dn-events-extensions:event-message-string "OSPF instance {instance}: Prefix-SID {sid-value} originated by {router-1-id} for {prefix-1} {algorithm-1} conflicts with Prefix-SID originated by {router-2-id} {algorithm-2} for {prefix-2}. Conflict resolved as {resolution}";
    dn-events-extensions:event-corrective-action-string "Change the Prefix-SID setting on either nodes.";
    dn-events-extensions:event-trigger-component-string "OSPF";
    dn-events-extensions:event-group "OSPF";
    leaf instance {
      type string;
      description
        "OSPF instance name";
    }
    leaf sid-value {
      type uint32;
      description
        "Absolute value of the Prefix-SID";
    }
    leaf router-1-id {
      type string;
      description
        "The router-id of remote node from which SID was received, if not known, display system-ID";
    }
    leaf prefix-1 {
      type string;
      description
        "The prefix for which node-1 advertise the Prefix-SID";
    }
    leaf algorithm-1 {
      description
        "The prefix-SID algorithm, SPF or S-SFP";
      type string;
    }
    leaf router-2-id {
      type string;
      description
        "The router-id of remote node from which SID was received, if not known, display system-ID";
    }
    leaf prefix-2 {
      type string;
      description
        "The prefix for which node-1 advertise the Prefix-SID";
    }
    leaf algorithm-2 {
      description
        "The prefix-SID algorithm, SPF or S-SFP";
      type string;
    }
    leaf resolution {
      type string;
      description
        "how conflict is resolved, i.e which prefix is assigned to sid";
    }
  }

  notification OSPF_SR_PREFIX_CONFLICT {
    description
      "Different Prefix-SIDs were received for the same Forwarding Equivalence Classes (FEC)s.";
    dn-events-extensions:event-severity-level "Warning";
    dn-events-extensions:event-message-string "OSPF instance {instance} Area {area-id} Prefix {ipv4-prefix} originated by {router-1-id} with Prefix-SID {sid-value-1} conflicts with Prefix-SID {sid-value-2} originated by {router-2-id}. Conflict resolved as {resolution}";
    dn-events-extensions:event-corrective-action-string "Change the Prefix-SID setting on either nodes.";
    dn-events-extensions:event-trigger-component-string "OSPF";
    dn-events-extensions:event-group "OSPF";
    leaf instance {
      type string;
      description
        "OSPF instance name";
    }
    leaf area-id {
      type string;
      description
        "area id";
    }
    leaf ipv4-prefix {
      type string;
      description
        "The prefix received from multiple nodes";
    }
    leaf router-1-id {
      type string;
      description
        "The router-id of remote node from which SID was received, if not known, display system-ID";
    }
    leaf sid-value-1 {
      type uint32;
      description
        "Absolute value of the Prefix-SID";
    }
    leaf sid-value-2 {
      type uint32;
      description
        "Absolute value of the Prefix-SID";
    }
    leaf router-2-id {
      type string;
      description
        "The router-id of remote node from which SID was received, if not known, display system-ID";
    }
    leaf resolution {
      type string;
      description
        "how conflict is resolved, i.e which prefix-sid is assigned to prefix";
    }
  }

  notification SR_SRGB_CONFIG_USER {
    description
      "The user listed changed the SRGB configuration.";
    dn-events-extensions:event-severity-level "Notice";
    dn-events-extensions:event-message-string "User {user-name} has configured the {config-level} Segement-Routing Global block. New block base: {base-sid}, range: {range}. Label Block reservation will take place at the next system restart";
    dn-events-extensions:event-corrective-action-string "Perform a system restart to apply the configuration changes.";
    dn-events-extensions:event-trigger-component-string "Segment-Routing";
    dn-events-extensions:event-group "Segment-Routing";
    leaf user-name {
      type string;
      description
        "User name";
    }
    leaf config-level {
      type string;
      description
        "Configuration level on which SRGB was changed, routing-options, ISIS or OSPF";
    }
    leaf base-sid {
      type uint32;
      description
        "Absolute value of the SRGB lower bound SID";
    }
    leaf range {
      type uint32;
      description
        "Range of the SRGB";
    }
  }

  notification SR_SRLB_CONFIG_USER {
    description
      "The user listed changed the SRLB configuration.";
    dn-events-extensions:event-severity-level "Notice";
    dn-events-extensions:event-message-string "User {user-name} has configured the {config-level} Segement-Routing Local block. New block base: {base-sid}, range: {range}. Label Block reservation will take place at the next system restart";
    dn-events-extensions:event-corrective-action-string "Perform a system restart to apply the configuration changes.";
    dn-events-extensions:event-trigger-component-string "Segment-Routing";
    dn-events-extensions:event-group "Segment-Routing";
    leaf user-name {
      type string;
      description
        "User name";
    }
    leaf config-level {
      type string;
      description
        "Configuration level on which SRLB was changed, routing-options, ISIS or OSPF";
    }
    leaf base-sid {
      type uint32;
      description
        "Absolute value of the SRLB lower bound SID";
    }
    leaf range {
      type uint32;
      description
        "Range of the SRLB";
    }
  }

  notification SR_POLICY_UP {
    description
      "The Segment-Routing policy moved to an 'up' state and can be used to forward traffic.";
    dn-events-extensions:event-severity-level "Info";
    dn-events-extensions:event-message-string "Segment-routing policy {policy-name} from {source-address} to {destination-address} with color {color}, switched to an UP state";
    dn-events-extensions:event-corrective-action-string "This is informational, no corrective action required.";
    dn-events-extensions:event-trigger-component-string "Segment-Routing";
    dn-events-extensions:event-group "Segment-Routing";
    dn-events-extensions:event-snmp-trap-name "dnSrPolicyUp";
    dn-events-extensions:event-snmp-trap-oid "1.3.6.1.4.1.49739.2.14.0.1";
    dn-events-extensions:event-snmp-trap-vars "dnSrPolicyName.0 {policy-name}; dnSrPolicySrcAddress.0 {source-address}; dnSrPolicyDestAddress.0 {destination-address}; dnSrPolicyColor.0 {color}";
    leaf policy-name {
      type string;
      description
        "Policy name";
    }
    leaf source-address {
      type string;
      description
        "Policy source IPv4/6 address";
    }
    leaf destination-address {
      type string;
      description
        "Policy destination IPv4 address";
    }
    leaf color {
      description
        "Policy color";
      type string;
    }
  }

  notification SR_POLICY_DOWN {
    description
      "The Segment-Routing policy moved to either 'down' or 'admin-down' state and cannot be used to forward traffic.";
    dn-events-extensions:event-severity-level "Warning";
    dn-events-extensions:event-message-string "Segment-routing policy {policy-name} from {source-address} to {destination-address} with color {color}, switched to an {state} state";
    dn-events-extensions:event-corrective-action-string "This is informational, no corrective action required.";
    dn-events-extensions:event-trigger-component-string "Segment-Routing";
    dn-events-extensions:event-group "Segment-Routing";
    dn-events-extensions:event-snmp-trap-name "dnSrPolicyDown";
    dn-events-extensions:event-snmp-trap-oid "1.3.6.1.4.1.49739.2.14.0.2";
    dn-events-extensions:event-snmp-trap-vars "dnSrPolicyName.0 {policy-name}; dnSrPolicySrcAddress.0 {source-address}; dnSrPolicyDestAddress.0 {destination-address}; dnSrPolicyColor.0 {color}; dnSrPolicyState.0 {state}";
    leaf policy-name {
      type string;
      description
        "Policy name";
    }
    leaf source-address {
      type string;
      description
        "Policy source IPv4 address";
    }
    leaf destination-address {
      type string;
      description
        "Policy destination IPv4 address";
    }
    leaf color {
      description
        "Policy color";
      type string;
    }
    leaf state {
      description
        "Policy new state, either down or admin-down";
      type enumeration {
        enum down {
          value 0;
        }
        enum admin-down {
          value 1;
        }
        enum down-cleanup {
          value 2;
        }
      }
    }
  }

  notification SR_POLICY_FAILED_COMPUTATION {
    description
      "All path options were found invalid for the Segment-Routing policy";
    dn-events-extensions:event-severity-level "Warning";
    dn-events-extensions:event-message-string "All path options were found invalid for the segment-routing policy {policy-name} from {source-address} to {destination-address} with color {color}";
    dn-events-extensions:event-corrective-action-string "Verify network connectivity and if used SIDs are valid";
    dn-events-extensions:event-trigger-component-string "Segment-Routing";
    dn-events-extensions:event-group "Segment-Routing";
    leaf policy-name {
      type string;
      description
        "Policy name";
    }
    leaf source-address {
      type string;
      description
        "Policy source IPv4 address";
    }
    leaf destination-address {
      type string;
      description
        "Policy destination IPv4 address";
    }
    leaf color {
      description
        "Policy color";
      type string;
    }
  }

  notification SR_POLICY_PATH_REOPTIMIZED {
    description
      "The Segment-Routing policy improved path in used and moved to a new path.";
    dn-events-extensions:event-severity-level "Info";
    dn-events-extensions:event-message-string "Segment-routing policy {policy-name} from {source-address} to {destination-address} with color {color}, changed active path from path {old-path-name} with priority {old-priority} to path {new-path-name} with priority {new-priority} due to {reoptimization-type} reoptimization.";
    dn-events-extensions:event-corrective-action-string "This is informational, no corrective action required.";
    dn-events-extensions:event-trigger-component-string "Segment-Routing";
    dn-events-extensions:event-group "Segment-Routing";
    leaf policy-name {
      type string;
      description
        "Policy name";
    }
    leaf source-address {
      type string;
      description
        "Policy source IPv4 address";
    }
    leaf destination-address {
      type string;
      description
        "Policy destination IPv4 address";
    }
    leaf color {
      description
        "Policy color";
      type string;
    }
    leaf old-path-name {
      description
        "The name of the path policy was previously using";
      type string;
    }
    leaf old-priority {
      description
        "Policy previous path option priority";
      type uint16;
    }
    leaf new-path-name {
      description
        "The name of the path policy has moved to";
      type string;
    }
    leaf new-priority {
      description
        "Policy new path option priority";
      type uint16;
    }
    leaf reoptimization-type {
      description
        "type of reoptimization trigger. could be one of the following: 'periodic', 'user-request', 'user-config'";
      type string;
    }
  }

  notification SR_POLICY_PATH_CHANGED {
    description
      "The Segment-Routing policy improved path in used and moved to a new path.";
    dn-events-extensions:event-severity-level "Notice";
    dn-events-extensions:event-message-string "Segment-routing policy {policy-name} from {source-address} to {destination-address} with color {color}, changed active path from path {old-path-name} with priority {old-priority} to path {new-path-name} with priority {new-priority} due to {reason}";
    dn-events-extensions:event-corrective-action-string "This is informational, no corrective action required.";
    dn-events-extensions:event-trigger-component-string "Segment-Routing";
    dn-events-extensions:event-group "Segment-Routing";
    leaf policy-name {
      type string;
      description
        "Policy name";
    }
    leaf source-address {
      type string;
      description
        "Policy source IPv4 address";
    }
    leaf destination-address {
      type string;
      description
        "Policy destination IPv4 address";
    }
    leaf color {
      description
        "Policy color";
      type string;
    }
    leaf old-path-name {
      description
        "The name of the path policy was previously using";
      type string;
    }
    leaf old-priority {
      description
        "Policy previous path option priority";
      type uint16;
    }
    leaf new-path-name {
      description
        "The name of the path policy has moved to";
      type string;
    }
    leaf new-priority {
      description
        "Policy new path option priority";
      type uint16;
    }
    leaf reason {
      description
        "reason for the path change. could be one of the following: 'path invalid'";
      type string;
    }
  }

  // ODN SR auto-policies

  notification SR_MAXIMUM_AUTO_POLICIES_LIMIT_REACHED {
    description
      "The maximum number of concurrent SR auto-policies has been reached.";
    dn-events-extensions:event-severity-level "Warning";
    dn-events-extensions:event-message-string "The system limit of {limit} SR auto-policies has been reached";
    dn-events-extensions:event-corrective-action-string "No corrective action.";
    dn-events-extensions:event-trigger-component-string "Segment-Routing";
    dn-events-extensions:event-group "Segment-Routing";
    leaf limit {
      type uint16;
      description
        "The configured SR auto-policies scale limit";
    }
  }

  notification SR_MAXIMUM_AUTO_POLICIES_LIMIT_CLEARED {
    description
      "The number of concurrent SR auto-policies has dropped below the configured maximum limit.";
    dn-events-extensions:event-severity-level "Info";
    dn-events-extensions:event-message-string "The number of SR auto-policies has dropped below the system limit of {limit} policies";
    dn-events-extensions:event-corrective-action-string "This is informational, no corrective action required.";
    dn-events-extensions:event-trigger-component-string "Segment-Routing";
    dn-events-extensions:event-group "Segment-Routing";
    leaf limit {
      type uint16;
      description
        "The configured SR auto-policies scale limit";
    }
  }

  notification SR_MAXIMUM_AUTO_POLICIES_THRESHOLD_EXCEEDED {
    description
      "The number of concurrent SR auto-policies has crossed the system threshold.";
    dn-events-extensions:event-severity-level "Notice";
    dn-events-extensions:event-message-string "The number of SR auto-policies has crossed the system threshold {threshold}% of the system limit of {limit} policies, the number of SR auto-policies is {numeric-value}";
    dn-events-extensions:event-corrective-action-string "No corrective action.";
    dn-events-extensions:event-trigger-component-string "Segment-Routing";
    dn-events-extensions:event-group "Segment-Routing";
    leaf threshold {
      type uint8;
      description
        "Threshold percent";
    }
    leaf numeric-value {
      type uint16;
      description
        "Current number of SR auto-policies";
    }
    leaf limit {
      type uint16;
      description
        "The configured SR auto-policies scale limit";
    }
  }

  notification SR_MAXIMUM_AUTO_POLICIES_THRESHOLD_CLEARED {
    description
      "The number of concurrent SR auto-policies has dropped below the configured system threshold.";
    dn-events-extensions:event-severity-level "Info";
    dn-events-extensions:event-message-string "The number of SR auto-policies has dropped below the system threshold {threshold}% of the system limit of {limit} policies, the number of SR auto-policies is {numeric-value}";
    dn-events-extensions:event-corrective-action-string "This is informational, no corrective action required.";
    dn-events-extensions:event-trigger-component-string "Segment-Routing";
    dn-events-extensions:event-group "Segment-Routing";
    leaf threshold {
      type uint8;
      description
        "Threshold percent";
    }
    leaf numeric-value {
      type uint16;
      description
        "Current number of SR auto-policies";
    }
    leaf limit {
      type uint16;
      description
        "The configured SR auto-policies scale limit";
    }
  }

  notification SR_POLICY_E2E_PROTECTION_UP {
    description
      "The SR-TE policy end-to-end protection backup path is up and installed.";
    dn-events-extensions:event-severity-level "Info";
    dn-events-extensions:event-message-string "Segment-Routing policy {policy-name} from {source-address} to {destination-address} with color {color} active path {active-path-name} priority {active-priority} is end-to-end protected by backup path {backup-path-name} priority {backup-priority}";
    dn-events-extensions:event-corrective-action-string "This is informational, no corrective action required.";
    dn-events-extensions:event-trigger-component-string "Segment-Routing";
    dn-events-extensions:event-group "Segment-Routing";
    leaf policy-name {
      description
        "policy name";
      type string;
    }
    leaf source-address {
      description
        "policy source IP address";
      type string;
    }
    leaf destination-address {
      description
        "policy destination IP address";
      type string;
    }
    leaf color {
      description
        "policy color";
      type string;
    }
    leaf active-path-name {
      description
        "active path name";
      type string;
    }
    leaf active-priority {
      description
        "active path name priority";
      type uint16;
    }
    leaf backup-path-name {
      description
        "backup path name";
      type string;
    }
    leaf backup-priority {
      description
        "backup path priority";
      type uint16;
    }
  }

  notification SR_POLICY_E2E_PROTECTION_DOWN {
    description
      "The SR-TE policy end-to-end protection backup path was removed.";
    dn-events-extensions:event-severity-level "Notice";
    dn-events-extensions:event-message-string "Segment-Routing policy {policy-name} from {source-address} to {destination-address} with color {color} active path {active-path-name} priority {active-priority} is no longer end-to-end protected";
    dn-events-extensions:event-corrective-action-string "Verify that the end-to-end backup path is valid.";
    dn-events-extensions:event-trigger-component-string "Segment-Routing";
    dn-events-extensions:event-group "Segment-Routing";
    leaf policy-name {
      description
        "policy name";
      type string;
    }
    leaf source-address {
      description
        "policy source IP address";
      type string;
    }
    leaf destination-address {
      description
        "policy destination IP address";
      type string;
    }
    leaf color {
      description
        "policy color";
      type string;
    }
    leaf active-path-name {
      description
        "active path name";
      type string;
    }
    leaf active-priority {
      description
        "active path name priority";
      type uint16;
    }
  }

  notification SRV6_TCAM_LIMIT_REACH {
    description
      "The TCAM resources allocated for SRv6 have reached the limit.";
    dn-events-extensions:event-severity-level "Warning";
    dn-events-extensions:event-message-string "The TCAM resources allocated for SRv6 have reached the limit of {limit} by protocol {protocol}.";
    dn-events-extensions:event-corrective-action-string "Reduce the SRv6 services or locators.";
    dn-events-extensions:event-trigger-component-string "Segment-Routing";
    dn-events-extensions:event-group "Segment-Routing";
    leaf limit {
      description
        "limit";
      type string;
    }
    leaf protocol {
      description
        "protocol";
      type string;
    }
  }

  notification SRV6_TCAM_LIMIT_RELEASED {
    description
      "The TCAM resources allocated for SRv6 have moved below the system limit.";
    dn-events-extensions:event-severity-level "Notice";
    dn-events-extensions:event-message-string "The TCAM resources allocated for SRv6 have moved below the system limit of {limit} by protocol {protocol}.";
    dn-events-extensions:event-corrective-action-string "This is informational, no corrective action required.";
    dn-events-extensions:event-trigger-component-string "Segment-Routing";
    dn-events-extensions:event-group "Segment-Routing";
    leaf limit {
      description
        "limit";
      type string;
    }
    leaf protocol {
      description
        "protocol";
      type string;
    }
  }

  notification SRV6_ISEM_LIMIT_REACH {
    description
      "The ISEM resources allocated for SRv6 have reached the limit.";
    dn-events-extensions:event-severity-level "Warning";
    dn-events-extensions:event-message-string "The ISEM resources allocated for SRv6 have reached the limit of {limit} by protocol {protocol}.";
    dn-events-extensions:event-corrective-action-string "Reduce the SRv6 services or locators.";
    dn-events-extensions:event-trigger-component-string "Segment-Routing";
    dn-events-extensions:event-group "Segment-Routing";
    leaf limit {
      description
        "limit";
      type string;
    }
    leaf protocol {
      description
        "protocol";
      type string;
    }
  }

  notification SRV6_ISEM_LIMIT_RELEASED {
    description
      "The ISEM resources allocated for SRv6 have moved below the system limit.";
    dn-events-extensions:event-severity-level "Notice";
    dn-events-extensions:event-message-string "The ISEM resources allocated for SRv6 have moved below the system limit of {limit} by protocol {protocol}.";
    dn-events-extensions:event-corrective-action-string "This is informational, no corrective action required.";
    dn-events-extensions:event-trigger-component-string "Segment-Routing";
    dn-events-extensions:event-group "Segment-Routing";
    leaf limit {
      description
        "limit";
      type string;
    }
    leaf protocol {
      description
        "protocol";
      type string;
    }
  }

  notification SRV6_CSID_BLOCK_DYNAMIC_RANGE_LIMIT_REACH {
    description
      "The SRv6 CSID allocations from the dynamic-function block have reached the limit.";
    dn-events-extensions:event-severity-level "Warning";
    dn-events-extensions:event-message-string "SRv6 CSID allocation for dynamic-function block {block_name} reached the system limit ({limit}), the current number of allocations is ({current_allocations}).";
    dn-events-extensions:event-corrective-action-string "Reduce the SRv6 services over locators in this block or increase the dynamic-function block size.";
    dn-events-extensions:event-trigger-component-string "Segment-Routing";
    dn-events-extensions:event-group "Segment-Routing";
    leaf block-name {
      description
        "block name";
      type string;
    }
    leaf limit {
      description
        "limit";
      type string;
    }
    leaf current-allocations {
      description
        "current allocations";
      type string;
    }
  }

  notification SRV6_CSID_BLOCK_STATIC_RANGE_LIMIT_REACH {
    description
      "SRv6 uSID allocation for static-function block reached the limit.";
    dn-events-extensions:event-severity-level "Warning";
    dn-events-extensions:event-message-string "SRv6 CSID allocation for static-function block {block_name} reached the system limit ({limit}), the current number of allocations is ({current_allocations}).";
    dn-events-extensions:event-corrective-action-string "Reduce the SRv6 services over locators in this block or increase the dynamic-function block size.";
    dn-events-extensions:event-trigger-component-string "Segment-Routing";
    dn-events-extensions:event-group "Segment-Routing";
    leaf block-name {
      description
        "block name";
      type string;
    }
    leaf limit {
      description
        "limit";
      type string;
    }
    leaf current-allocations {
      description
        "current allocations";
      type string;
    }
  }

  notification SRV6_CSID_BLOCK_DYNAMIC_RANGE_THRESHOLD_REACH {
    description
      "SRv6 CSID allocation for dynamic-function block crossed the system threshold.";
    dn-events-extensions:event-severity-level "Warning";
    dn-events-extensions:event-message-string "SRv6 CSID allocation for dynamic-function block {block_name} crossed the system threshold, 90% of the limit ({limit}), the current number of allocations is ({current_allocations}).";
    dn-events-extensions:event-corrective-action-string "Reduce the SRv6 services over locators in this block.";
    dn-events-extensions:event-trigger-component-string "Segment-Routing";
    dn-events-extensions:event-group "Segment-Routing";
    leaf block-name {
      description
        "block name";
      type string;
    }
    leaf limit {
      description
        "limit";
      type string;
    }
    leaf current-allocations {
      description
        "current allocations";
      type string;
    }
  }

  notification SRV6_CSID_BLOCK_DYNAMIC_RANGE_THRESHOLD_CLEAR {
    description
      "The threshold of SRv6 CSID allocation for dynamic-function block was cleared.";
    dn-events-extensions:event-severity-level "Info";
    dn-events-extensions:event-message-string "SRv6 CSID allocation for dynamic-function block {block_name} is below the threshold (85%) of the limit ({limit}), the current number of allocations is ({current_allocations}).";
    dn-events-extensions:event-corrective-action-string "This is informational, no corrective action required";
    dn-events-extensions:event-trigger-component-string "Segment-Routing";
    dn-events-extensions:event-group "Segment-Routing";
    leaf block-name {
      description
        "block name";
      type string;
    }
    leaf limit {
      description
        "limit";
      type string;
    }
    leaf current-allocations {
      description
        "current allocations";
      type string;
    }
  }

  notification SRV6_CSID_BLOCK_STATIC_RANGE_THRESHOLD_REACH {
    description
      "SRv6 CSID allocation for static-function block crossed the system threshold.";
    dn-events-extensions:event-severity-level "Warning";
    dn-events-extensions:event-message-string "SRv6 CSID allocation for static-function block {block_name} crossed the system threshold, 90% of the limit ({limit}), the current number of allocations is ({current_allocations}).";
    dn-events-extensions:event-corrective-action-string "Reduce the SRv6 services over locators in this block.";
    dn-events-extensions:event-trigger-component-string "Segment-Routing";
    dn-events-extensions:event-group "Segment-Routing";
    leaf block-name {
      description
        "block name";
      type string;
    }
    leaf limit {
      description
        "limit";
      type string;
    }
    leaf current-allocations {
      description
        "current allocations";
      type string;
    }
  }

  notification SRV6_CSID_BLOCK_STATIC_RANGE_THRESHOLD_CLEAR {
    description
      "The threshold of SRv6 CSID allocation for static-function block was cleared.";
    dn-events-extensions:event-severity-level "Info";
    dn-events-extensions:event-message-string "SRv6 CSID allocation for static-function block {block_name} is below the threshold (85%) of the limit ({limit}), the current number of allocations is ({current_allocations}).";
    dn-events-extensions:event-corrective-action-string "This is informational, no corrective action required";
    dn-events-extensions:event-trigger-component-string "Segment-Routing";
    dn-events-extensions:event-group "Segment-Routing";
    leaf block-name {
      description
        "block name";
      type string;
    }
    leaf limit {
      description
        "limit";
      type string;
    }
    leaf current-allocations {
      description
        "current allocations";
      type string;
    }
  }

  // RSVP events

  notification RSVP_TUNNEL_UP {
    description
      "The RSVP tunnel moved to an 'up' state and can be used to forward traffic.";
    dn-events-extensions:event-severity-level "Info";
    dn-events-extensions:event-message-string "RSVP tunnel {tunnel-name} from {source-address} to {destination-address}, tunnel ID {tunnel-id}, LSP ID {lsp-id}, switched to an up state";
    dn-events-extensions:event-corrective-action-string "This is informational, no corrective action required.";
    dn-events-extensions:event-trigger-component-string "RSVP";
    dn-events-extensions:event-group "RSVP";
    dn-events-extensions:event-snmp-trap-name "mplsTunnelUp";
    dn-events-extensions:event-snmp-trap-oid "1.3.6.1.2.1.10.166.3.0.1";
    dn-events-extensions:event-snmp-trap-vars "mplsTunnelAdminStatus.{tunnel-id}.{lsp-id}.{ingress-lsr-id}.{egress-lsr-id} {admin-status} ; mplsTunnelOperStatus.{tunnel-id}.{lsp-id}.{ingress-lsr-id}.{egress-lsr-id} {oper-status} ";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type uint32 {
        range "0..65535";
      }
    }
    leaf lsp-id {
      description
        "LSP ID";
      type uint32;
    }
    leaf admin-status {
      type enumeration {
        enum up {
          value 1;
        }
        enum down {
          value 2;
        }
        enum testing {
          value 3;
        }
      }
      description
        "Indicates the desired operational status of this
         tunnel";
    }
    leaf oper-status {
      type enumeration {
        enum up {
          value 1;
        }
        enum down {
          value 2;
        }
        enum testing {
          value 3;
        }
        enum unknown {
          value 4;
        }
        enum dormant {
          value 5;
        }
        enum notPresent {
          value 6;
        }
        enum lowerLayerDown {
          value 7;
        }
      }
      description
        "Indicates the actual operational status of this
         tunnel, which is typically but not limited to, a
         function of the state of individual segments of
         this tunnel";
    }
    leaf ingress-lsr-id {
      description
        "uint32 value of the tunnel source-address
         SNMP: Identity of the ingress LSR associated with this
         tunnel instance. When the MPLS signalling protocol
         is rsvp(2) this value SHOULD be equal to the Tunnel
         Sender Address in the Sender Template object and MAY
         be equal to the Extended Tunnel Id field in the
         SESSION object. When the MPLS signalling protocol is
         crldp(3) this value SHOULD be equal to the Ingress
         LSR Router ID field in the LSPID TLV object.";
      type uint32;
    }
    leaf egress-lsr-id {
      description
        "uint32 value of the tunnel destination address
         SNMP: Identity of the egress LSR associated with this
         tunnel instance.";
      type uint32;
    }
  }

  notification RSVP_TUNNEL_DOWN {
    description
      "The RSVP tunnel moved to a 'down' state and so cannot be used to forward traffic.";
    dn-events-extensions:event-severity-level "Critical";
    dn-events-extensions:event-message-string "RSVP tunnel {tunnel-name} from {source-address} to {destination-address}, tunnel ID {tunnel-id}, LSP ID {lsp-id}, switched to a down state due to {reason}";
    dn-events-extensions:event-corrective-action-string "No corrective action.";
    dn-events-extensions:event-trigger-component-string "RSVP";
    dn-events-extensions:event-group "RSVP";
    dn-events-extensions:event-snmp-trap-name "mplsTunnelDown";
    dn-events-extensions:event-snmp-trap-oid "1.3.6.1.2.1.10.166.3.0.2";
    dn-events-extensions:event-snmp-trap-vars "mplsTunnelAdminStatus.{tunnel-id}.{lsp-id}.{ingress-lsr-id}.{egress-lsr-id} {admin-status} ; mplsTunnelOperStatus.{tunnel-id}.{lsp-id}.{ingress-lsr-id}.{egress-lsr-id} {oper-status} ";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type uint32 {
        range "0..65535";
      }
    }
    leaf lsp-id {
      description
        "LSP ID";
      type uint32;
    }
    leaf reason {
      description
        "Reason for tunnel going down";
      type string;
    }
    leaf admin-status {
      type enumeration {
        enum up {
          value 1;
        }
        enum down {
          value 2;
        }
        enum testing {
          value 3;
        }
      }
      description
        "Indicates the desired operational status of this
         tunnel";
    }
    leaf oper-status {
      type enumeration {
        enum up {
          value 1;
        }
        enum down {
          value 2;
        }
        enum testing {
          value 3;
        }
        enum unknown {
          value 4;
        }
        enum dormant {
          value 5;
        }
        enum notPresent {
          value 6;
        }
        enum lowerLayerDown {
          value 7;
        }
      }
      description
        "Indicates the actual operational status of this
         tunnel, which is typically but not limited to, a
         function of the state of individual segments of
         this tunnel";
    }
    leaf ingress-lsr-id {
      description
        "uint32 value of the tunnel source-address
         SNMP: Identity of the ingress LSR associated with this
         tunnel instance. When the MPLS signalling protocol
         is rsvp(2) this value SHOULD be equal to the Tunnel
         Sender Address in the Sender Template object and MAY
         be equal to the Extended Tunnel Id field in the
         SESSION object. When the MPLS signalling protocol is
         crldp(3) this value SHOULD be equal to the Ingress
         LSR Router ID field in the LSPID TLV object.";
      type uint32;
    }
    leaf egress-lsr-id {
      description
        "uint32 value of the tunnel destination address
         SNMP: Identity of the egress LSR associated with this
         tunnel instance.";
      type uint32;
    }
  }

  notification RSVP_LSP_EVENT {
    description
      "There is an error with the Label Switched Path (LSP) for the RSVP tunnel, and is moving to a 'down' state.";
    dn-events-extensions:event-severity-level "Warning";
    dn-events-extensions:event-message-string "RSVP tunnel {tunnel-name} from {source-address} to {destination-address}, tunnel ID {tunnel-id}, LSP ID {lsp-id}, has encountered {event} event. LSP bandwidth {bandwidth} kbps, originated from {originator}";
    dn-events-extensions:event-corrective-action-string "No corrective action.";
    dn-events-extensions:event-trigger-component-string "RSVP";
    dn-events-extensions:event-group "RSVP";
    leaf tunnel-name {
      type string;
      description
        "Tunnel name";
    }
    leaf source-address {
      type string;
      description
        "LSP source IPv4 address";
    }
    leaf destination-address {
      type string;
      description
        "LSP destination IPv4 address";
    }
    leaf tunnel-id {
      description
        "Tunnel local ID";
      type string;
    }
    leaf lsp-id {
      type string;
      description
        "LSP unique local ID";
    }
    leaf event {
      type string;
      description
        "Event code";
    }
    leaf bandwidth {
      description
        "LSP requested bandwidth in kbps";
      type string;
    }
    leaf originator {
      type string;
      description
        "Originator IPv4 address";
    }
  }

  notification RSVP_TUNNEL_REROUTED {
    description
      "The RSVP tunnel switched to a bypass tunnel somewhere along the tunnel path.";
    dn-events-extensions:event-severity-level "Warning";
    dn-events-extensions:event-message-string "RSVP tunnel {tunnel-name} from {source-address} to {destination-address}, tunnel ID {tunnel-id}, LSP ID {lsp-id}, moved on a bypass tunnel, {event}, originated from {originator}.";
    dn-events-extensions:event-corrective-action-string "This is informational, no corrective action required.";
    dn-events-extensions:event-trigger-component-string "RSVP";
    dn-events-extensions:event-group "RSVP";
    dn-events-extensions:event-snmp-trap-name "mplsTunnelRerouted";
    dn-events-extensions:event-snmp-trap-oid "1.3.6.1.2.1.10.166.3.0.3";
    dn-events-extensions:event-snmp-trap-vars "mplsTunnelAdminStatus.{tunnel-id}.{lsp-id}.{ingress-lsr-id}.{egress-lsr-id} {admin-status} ; mplsTunnelOperStatus.{tunnel-id}.{lsp-id}.{ingress-lsr-id}.{egress-lsr-id} {oper-status} ";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type uint32 {
        range "0..65535";
      }
    }
    leaf lsp-id {
      description
        "LSP ID";
      type uint32;
    }
    leaf admin-status {
      type enumeration {
        enum up {
          value 1;
        }
        enum down {
          value 2;
        }
        enum testing {
          value 3;
        }
      }
      description
        "Indicates the desired operational status of this
         tunnel";
    }
    leaf oper-status {
      type enumeration {
        enum up {
          value 1;
        }
        enum down {
          value 2;
        }
        enum testing {
          value 3;
        }
        enum unknown {
          value 4;
        }
        enum dormant {
          value 5;
        }
        enum notPresent {
          value 6;
        }
        enum lowerLayerDown {
          value 7;
        }
      }
      description
        "Indicates the actual operational status of this
         tunnel, which is typically but not limited to, a
         function of the state of individual segments of
         this tunnel";
    }
    leaf ingress-lsr-id {
      description
        "uint32 value of the tunnel source-address
         SNMP: Identity of the ingress LSR associated with this
         tunnel instance. When the MPLS signalling protocol
         is rsvp(2) this value SHOULD be equal to the Tunnel
         Sender Address in the Sender Template object and MAY
         be equal to the Extended Tunnel Id field in the
         SESSION object. When the MPLS signalling protocol is
         crldp(3) this value SHOULD be equal to the Ingress
         LSR Router ID field in the LSPID TLV object.";
      type uint32;
    }
    leaf egress-lsr-id {
      description
        "uint32 value of the tunnel destination address
         SNMP: Identity of the egress LSR associated with this
         tunnel instance.";
      type uint32;
    }
    leaf event {
      type string;
      description
        "Event code";
    }
    leaf originator {
      type string;
      description
        "Originator IPv4 address";
    }
  }

  notification RSVP_TUNNEL_LSP_SWITCH {
    description
      "The RSVP tunnel switched between primary and secondary lsp.";
    dn-events-extensions:event-severity-level "Notice";
    dn-events-extensions:event-message-string "RSVP tunnel {tunnel-name} from {source-address} to {destination-address}, tunnel ID {tunnel-id}, switch from {previous-active-lsp} LSP ID {previous-lsp-id} to {new-active-lsp} LSP ID {new-lsp-id}. Reason: {reason}";
    dn-events-extensions:event-corrective-action-string "This is informational, no corrective action required.";
    dn-events-extensions:event-trigger-component-string "RSVP";
    dn-events-extensions:event-group "RSVP";
    dn-events-extensions:event-snmp-trap-name "mplsTunnelRerouted";
    dn-events-extensions:event-snmp-trap-oid "1.3.6.1.2.1.10.166.3.0.3";
    dn-events-extensions:event-snmp-trap-vars "mplsTunnelAdminStatus.{tunnel-id}.{new-lsp-id}.{ingress-lsr-id}.{egress-lsr-id} {admin-status} ; mplsTunnelOperStatus.{tunnel-id}.{new-lsp-id}.{ingress-lsr-id}.{egress-lsr-id} {oper-status} ";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type uint32 {
        range "0..65535";
      }
    }
    leaf previous-active-lsp {
      description
        "Previous active lsp type, either primary or secondary";
      type enumeration {
        enum primary;
        enum secondary;
      }
    }
    leaf new-active-lsp {
      description
        "New active lsp type, either primary or secondary";
      type enumeration {
        enum primary;
        enum secondary;
      }
    }
    leaf previous-lsp-id {
      description
        "LSP ID";
      type uint32;
    }
    leaf new-lsp-id {
      description
        "LSP ID";
      type uint32;
    }
    leaf reason {
      description
        "reason for tunnel lsp switchover";
      type string;
    }
    leaf admin-status {
      type enumeration {
        enum up {
          value 1;
        }
        enum down {
          value 2;
        }
        enum testing {
          value 3;
        }
      }
      description
        "Indicates the desired operational status of this
         tunnel";
    }
    leaf oper-status {
      type enumeration {
        enum up {
          value 1;
        }
        enum down {
          value 2;
        }
        enum testing {
          value 3;
        }
        enum unknown {
          value 4;
        }
        enum dormant {
          value 5;
        }
        enum notPresent {
          value 6;
        }
        enum lowerLayerDown {
          value 7;
        }
      }
      description
        "Indicates the actual operational status of this
         tunnel, which is typically but not limited to, a
         function of the state of individual segments of
         this tunnel";
    }
    leaf ingress-lsr-id {
      description
        "uint32 value of the tunnel source-address
         SNMP: Identity of the ingress LSR associated with this
         tunnel instance. When the MPLS signalling protocol
         is rsvp(2) this value SHOULD be equal to the Tunnel
         Sender Address in the Sender Template object and MAY
         be equal to the Extended Tunnel Id field in the
         SESSION object. When the MPLS signalling protocol is
         crldp(3) this value SHOULD be equal to the Ingress
         LSR Router ID field in the LSPID TLV object.";
      type uint32;
    }
    leaf egress-lsr-id {
      description
        "uint32 value of the tunnel destination address
         SNMP: Identity of the egress LSR associated with this
         tunnel instance.";
      type uint32;
    }
  }

  notification RSVP_TUNNEL_E2E_PROTECTION_UP {
    description
      "The RSVP tunnel end-to-end protection lsp is Up and installed as alternate path";
    dn-events-extensions:event-severity-level "Info";
    dn-events-extensions:event-message-string "RSVP tunnel {tunnel-name} from {source-address} to {destination-address}, tunnel ID {tunnel-id}, with active lsp {active-lsp-id} is end-to-end protected by alternate lsp {alternate-lsp-id}";
    dn-events-extensions:event-corrective-action-string "This is informational, no corrective action required.";
    dn-events-extensions:event-trigger-component-string "RSVP";
    dn-events-extensions:event-group "RSVP";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type uint32 {
        range "0..65535";
      }
    }
    leaf active-lsp-id {
      description
        "LSP ID";
      type uint32;
    }
    leaf alternate-lsp-id {
      description
        "LSP ID";
      type uint32;
    }
  }

  notification RSVP_TUNNEL_E2E_PROTECTION_DOWN {
    description
      "The RSVP tunnel end-to-end protection lsp is Up and installed as alternate path";
    dn-events-extensions:event-severity-level "Notice";
    dn-events-extensions:event-message-string "RSVP tunnel {tunnel-name} from {source-address} to {destination-address}, tunnel ID {tunnel-id}, with active lsp {active-lsp-id} is no longer end-to-end protected";
    dn-events-extensions:event-corrective-action-string "Verify the end-to-end protection is expected and if alternate lsp didn't fail";
    dn-events-extensions:event-trigger-component-string "RSVP";
    dn-events-extensions:event-group "RSVP";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type uint32 {
        range "0..65535";
      }
    }
    leaf active-lsp-id {
      description
        "LSP ID";
      type uint32;
    }
  }

  notification RSVP_TUNNEL_OPTIMIZED {
    description
      "The RSVP tunnel listed is being optimized.";
    dn-events-extensions:event-severity-level "Info";
    dn-events-extensions:event-message-string "RSVP tunnel {tunnel-name} from {source-address} to {destination-address}, tunnel ID {tunnel-id}, has been optimized due to {reason}. New LSP ID: {new-lsp-id}, old LSP ID: {old-lsp-id}. Tunnel requested bandwidth: {bandwidth} kbps.";
    dn-events-extensions:event-corrective-action-string "This is informational, no corrective action required.";
    dn-events-extensions:event-trigger-component-string "RSVP";
    dn-events-extensions:event-group "RSVP";
    dn-events-extensions:event-snmp-trap-name "mplsTunnelReoptimized";
    dn-events-extensions:event-snmp-trap-oid "1.3.6.1.2.1.10.166.3.0.4";
    dn-events-extensions:event-snmp-trap-vars "mplsTunnelAdminStatus.{tunnel-id}.{new-lsp-id}.{ingress-lsr-id}.{egress-lsr-id} {admin-status} ; mplsTunnelOperStatus.{tunnel-id}.{new-lsp-id}.{ingress-lsr-id}.{egress-lsr-id} {oper-status} ";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type uint32 {
        range "0..65535";
      }
    }
    leaf reason {
      description
        "Tunnel MBB reason";
      type string;
    }
    leaf new-lsp-id {
      description
        "LSP ID";
      type uint32;
    }
    leaf old-lsp-id {
      description
        "Old LSP ID";
      type string;
    }
    leaf bandwidth {
      description
        "Tunnel requested bandwidth in kbps";
      type string;
    }
    leaf admin-status {
      type enumeration {
        enum up {
          value 1;
        }
        enum down {
          value 2;
        }
        enum testing {
          value 3;
        }
      }
      description
        "Indicates the desired operational status of this
         tunnel";
    }
    leaf oper-status {
      type enumeration {
        enum up {
          value 1;
        }
        enum down {
          value 2;
        }
        enum testing {
          value 3;
        }
        enum unknown {
          value 4;
        }
        enum dormant {
          value 5;
        }
        enum notPresent {
          value 6;
        }
        enum lowerLayerDown {
          value 7;
        }
      }
      description
        "Indicates the actual operational status of this
         tunnel, which is typically but not limited to, a
         function of the state of individual segments of
         this tunnel";
    }
    leaf ingress-lsr-id {
      description
        "uint32 value of the tunnel source-address
         SNMP: Identity of the ingress LSR associated with this
         tunnel instance. When the MPLS signalling protocol
         is rsvp(2) this value SHOULD be equal to the Tunnel
         Sender Address in the Sender Template object and MAY
         be equal to the Extended Tunnel Id field in the
         SESSION object. When the MPLS signalling protocol is
         crldp(3) this value SHOULD be equal to the Ingress
         LSR Router ID field in the LSPID TLV object.";
      type uint32;
    }
    leaf egress-lsr-id {
      description
        "uint32 value of the tunnel destination address
         SNMP: Identity of the egress LSR associated with this
         tunnel instance.";
      type uint32;
    }
  }

  notification RSVP_FRR_ACTIVE {
    description
      "The RSVP bypass tunnel has become active and is providing protection for the interface.";
    dn-events-extensions:event-severity-level "Info";
    dn-events-extensions:event-message-string "RSVP bypass tunnel {tunnel-name} from {source-address} to {destination-address}, tunnel ID {tunnel-id}, LSP ID {lsp-id} is active. Protecting interface {interface-name}. Protected bandwidth {bandwidth} kbps";
    dn-events-extensions:event-corrective-action-string "No corrective action.";
    dn-events-extensions:event-trigger-component-string "RSVP";
    dn-events-extensions:event-group "RSVP";
    dn-events-extensions:event-snmp-trap-name "dnRsvpFrrActive";
    dn-events-extensions:event-snmp-trap-oid ".1.3.6.1.4.1.49739.2.10.0.1";
    dn-events-extensions:event-snmp-trap-vars "dnTunnelName.0 {tunnel-name} ; dnSourceAddress.0 {source-address} ; dnDestinationAddress.0 {destination-address} ; dnTunnelId.0 {tunnel-id} ; dnLspId.0 {lsp-id} ; dnInterfaceName.0 {interface-name} ; dnBandwidth.0 {bandwidth}";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type string;
    }
    leaf lsp-id {
      description
        "LSP ID";
      type string;
    }
    leaf interface-name {
      description
        "Protected interface name";
      type string;
    }
    leaf bandwidth {
      description
        "Aggregated bandwidth of all protected tunnels";
      type string;
    }
  }

  notification RSVP_FRR_INACTIVE {
    description
      "The RSVP bypass tunnel became inactive and no longer provides protection.";
    dn-events-extensions:event-severity-level "Info";
    dn-events-extensions:event-message-string "RSVP bypass tunnel {tunnel-name} from {source-address} to {destination-address}, tunnel ID {tunnel-id}, LSP ID {lsp-id} is inactive. Protecting interface {interface-name}";
    dn-events-extensions:event-corrective-action-string "No corrective action.";
    dn-events-extensions:event-trigger-component-string "RSVP";
    dn-events-extensions:event-group "RSVP";
    dn-events-extensions:event-snmp-trap-name "dnRsvpFrrInactive";
    dn-events-extensions:event-snmp-trap-oid ".1.3.6.1.4.1.49739.2.10.0.2";
    dn-events-extensions:event-snmp-trap-vars "dnTunnelName.0 {tunnel-name} ; dnSourceAddress.0 {source-address} ; dnDestinationAddress.0 {destination-address} ; dnTunnelId.0 {tunnel-id} ; dnLspId.0 {lsp-id} ; dnInterfaceName.0 {interface-name}";
    leaf tunnel-name {
      type string;
      description
        "Tunnel name";
    }
    leaf source-address {
      type string;
      description
        "Tunnel source IPv4 address";
    }
    leaf destination-address {
      type string;
      description
        "Tunnel destination IPv4 address";
    }
    leaf tunnel-id {
      description
        "Tunnel local ID";
      type string;
    }
    leaf lsp-id {
      description
        "LSP ID";
      type string;
    }
    leaf interface-name {
      description
        "Protected interface name";
      type string;
    }
  }

  notification RSVP_INTERNAL_ERROR {
    description
      "The RSVP process has failed due to an internal error.";
    dn-events-extensions:event-severity-level "Error";
    dn-events-extensions:event-message-string "RSVP process has encountered an error: {error-type}, {error-message}";
    dn-events-extensions:event-corrective-action-string "Copy the error message and contact Customer Support.";
    dn-events-extensions:event-trigger-component-string "RSVP";
    dn-events-extensions:event-group "RSVP";
    leaf error-type {
      type string;
      description
        "Error group type";
    }
    leaf error-message {
      type string;
      description
        "Error description";
    }
  }

  notification RSVP_TUNNEL_AUTOBW_ADJUST_USER {
    description
      "The user listed performed an auto-bandwidth adjustment operation for the RSVP tunnel.";
    dn-events-extensions:event-severity-level "Info";
    dn-events-extensions:event-message-string "User {user-name} has performed auto-bandwidth adjustment operation for {tunnel-name} RSVP tunnel";
    dn-events-extensions:event-corrective-action-string "This is informational, no corrective action required.";
    dn-events-extensions:event-trigger-component-string "RSVP";
    dn-events-extensions:event-group "RSVP";
    leaf user-name {
      type string;
      description
        "User name";
    }
    leaf tunnel-name {
      type string;
      description
        "RSVP tunnel name or all if user set for all tunnels";
    }
  }

  notification RSVP_TUNNEL_AUTOBW_ADJUST_BW_USER {
    description
      "The user listed performed an auto-bandwidth bandwidth adjustment operation for the RSVP tunnel.";
    dn-events-extensions:event-severity-level "Info";
    dn-events-extensions:event-message-string "User {user-name} has performed auto-bandwidth bandwidth {bandwidth} adjustment operation for {tunnel-name} RSVP tunnel";
    dn-events-extensions:event-corrective-action-string "This is informational, no corrective action required.";
    dn-events-extensions:event-trigger-component-string "RSVP";
    dn-events-extensions:event-group "RSVP";
    leaf user-name {
      type string;
      description
        "User name";
    }
    leaf bandwidth {
      type uint64;
      description
        "RSVP tunnel bandwidth, in kbps";
    }
    leaf tunnel-name {
      type string;
      description
        "RSVP tunnel name or all if user set for all tunnels";
    }
  }

  notification RSVP_CBTS_ADMIN_STATE_CONFIG {
    description
      "The user listed changed the RSVP CBTS admin-state.";
    dn-events-extensions:event-severity-level "Info";
    dn-events-extensions:event-message-string "User {user-name} has changed RSVP CBTS admin-state to {new-state}";
    dn-events-extensions:event-corrective-action-string "This is informational, no corrective action required.";
    dn-events-extensions:event-trigger-component-string "Transaction-manager";
    dn-events-extensions:event-group "RSVP";
    leaf user-name {
      type string;
      description
        "User name";
    }
    leaf new-state {
      type enumeration {
        enum enabled;
        enum disabled;
      }
      description
        "CBTS new admin-state";
    }
  }

  notification RSVP_MAXIMUM_TUNNELS_LIMIT_REACHED {
    description
      "The number of concurrent RSVP tunnels has reached the maximum number of LSP tunnels.";
    dn-events-extensions:event-severity-level "Warning";
    dn-events-extensions:event-message-string "Number of RSVP tunnels has reached the system limit of {limit} LSP tunnels";
    dn-events-extensions:event-corrective-action-string "No corrective action.";
    dn-events-extensions:event-trigger-component-string "RSVP";
    dn-events-extensions:event-group "RSVP";
    leaf limit {
      type uint16;
      description
        "The accumulated tunnel scale limit (head + transit + tail)";
    }
  }

  notification RSVP_MAXIMUM_TUNNELS_LIMIT_CLEARED {
    description
      "The number of concurrent RSVP tunnels is below the configured maximum limit of LSP tunnels.";
    dn-events-extensions:event-severity-level "Info";
    dn-events-extensions:event-message-string "Number of RSVP tunnels is below the system limit of {limit}";
    dn-events-extensions:event-corrective-action-string "This is informational, no corrective action required.";
    dn-events-extensions:event-trigger-component-string "RSVP";
    dn-events-extensions:event-group "RSVP";
    leaf limit {
      type uint16;
      description
        "The accumulated tunnel scale limit (head + transit + tail)";
    }
  }

  notification RSVP_MAXIMUM_TUNNELS_THRESHOLD_EXCEEDED {
    description
      "The number of RSVP tunnels crossed the maximum supported threshold.";
    dn-events-extensions:event-severity-level "Notice";
    dn-events-extensions:event-message-string "Number of RSVP tunnels has crossed the system threshold {threshold}% of the limit ({limit}), the number of LSP tunnels are ({numeric-value})";
    dn-events-extensions:event-corrective-action-string "No corrective action.";
    dn-events-extensions:event-trigger-component-string "RSVP";
    dn-events-extensions:event-group "RSVP";
    leaf threshold {
      type uint8;
      description
        "Threshold percent";
    }
    leaf numeric-value {
      type uint16;
      description
        "Current number of RSVP tunnels";
    }
    leaf limit {
      type uint16;
      description
        "The accumulated tunnel scale limit (head + transit + tail)";
    }
  }

  notification RSVP_MAXIMUM_TUNNELS_THRESHOLD_CLEARED {
    description
      "The number of concurrent RSVP tunnels is below the configured maximum threshold of LSP tunnels.";
    dn-events-extensions:event-severity-level "Info";
    dn-events-extensions:event-message-string "Number of RSVP tunnels is below the threshold {threshold}% of the limit ({limit}), the number of LSP tunnels are ({numeric-value})";
    dn-events-extensions:event-corrective-action-string "This is informational, no corrective action required.";
    dn-events-extensions:event-trigger-component-string "RSVP";
    dn-events-extensions:event-group "RSVP";
    leaf threshold {
      type uint8;
      description
        "Threshold percent";
    }
    leaf numeric-value {
      type uint16;
      description
        "Current number of RSVP tunnels";
    }
    leaf limit {
      type uint16;
      description
        "The accumulated tunnel scale limit (head + transit + tail)";
    }
  }

  notification RSVP_MAXIMUM_HEAD_TUNNELS_LIMIT_REACHED {
    description
      "The number of concurrent RSVP head tunnels has reached the maximum number of tunnels.";
    dn-events-extensions:event-severity-level "Warning";
    dn-events-extensions:event-message-string "Number of RSVP head tunnels has reached the system limit of {limit} head tunnels";
    dn-events-extensions:event-corrective-action-string "Remove unnecessary RSVP tunnels.";
    dn-events-extensions:event-trigger-component-string "RSVP";
    dn-events-extensions:event-group "RSVP";
    leaf limit {
      description
        "Max number of head tunnels";
      type string;
    }
  }

  notification RSVP_MAXIMUM_HEAD_TUNNELS_LIMIT_CLEARED {
    description
      "The number of concurrent RSVP head tunnels is below the system limit of 250 tunnels.";
    dn-events-extensions:event-severity-level "Info";
    dn-events-extensions:event-message-string "Number of RSVP tunnels is below the system limit of {limit} head tunnels";
    dn-events-extensions:event-corrective-action-string "This is informational, no corrective action required.";
    dn-events-extensions:event-trigger-component-string "RSVP";
    dn-events-extensions:event-group "RSVP";
    leaf limit {
      description
        "Max number of head tunnels";
      type string;
    }
  }

  // PCEP events

  notification PCEP_SESSION_UP {
    description
      "The PCEP session with the listed PCE server has moved from a 'down' state to an 'up' state.";
    dn-events-extensions:event-severity-level "Info";
    dn-events-extensions:event-message-string "PCEP session with PCE server {server-address} established. PCE priority {priority}";
    dn-events-extensions:event-corrective-action-string "This is informational, no corrective action required.";
    dn-events-extensions:event-trigger-component-string "RSVP";
    dn-events-extensions:event-group "PCEP";
    leaf server-address {
      type string;
      description
        "The PCE server address";
    }
    leaf priority {
      type uint8;
      description
        "The PCE server priority";
    }
  }

  notification PCEP_SESSION_DOWN {
    description
      "The PCEP session with the listed PCE server has moved from an 'up' state to a 'down' state.";
    dn-events-extensions:event-severity-level "Warning";
    dn-events-extensions:event-message-string "PCEP session with PCE server {server-address} disconnected. PCE server priority {priority}";
    dn-events-extensions:event-corrective-action-string "No corrective action.";
    dn-events-extensions:event-trigger-component-string "RSVP";
    dn-events-extensions:event-group "PCEP";
    leaf server-address {
      type string;
      description
        "The PCE server address";
    }
    leaf priority {
      type uint8;
      description
        "The PCE server priority";
    }
  }

  notification PCEP_TUNNEL_LSP_DELEGATION_CHANGE {
    description
      "The RSVP tunnel changed its PCEP delegation state from either 'enabled' to 'disabled' or 'disabled' to 'enabled'.";
    dn-events-extensions:event-severity-level "Notice";
    dn-events-extensions:event-message-string "RSVP tunnel {tunnel-name} is {delegation-status} to  PCE {pce-address}";
    dn-events-extensions:event-corrective-action-string "No corrective action.";
    dn-events-extensions:event-trigger-component-string "RSVP";
    dn-events-extensions:event-group "PCEP";
    leaf tunnel-name {
      type string;
      description
        "Tunnel name";
    }
    leaf delegation-status {
      description
        "Tunnel operational delegation status, either 'delegated' or 'no longer delegated'";
      type string;
    }
    leaf pce-address {
      description
        "PCE IP address";
      type string;
    }
  }

  notification PCEP_MESSAGE_ERROR {
    description
      "The PCEP server has sent an error message listed.";
    dn-events-extensions:event-severity-level "Notice";
    dn-events-extensions:event-message-string "PCC {direction} PCEP server {server-address} with priority {priority} an error message {description} (type {type}, value {value})";
    dn-events-extensions:event-corrective-action-string "No corrective action.";
    dn-events-extensions:event-trigger-component-string "RSVP";
    dn-events-extensions:event-group "PCEP";
    leaf direction {
      description
        "Indicate whether PCC sent or received the error msg";
      type enumeration {
        enum sent_to;
        enum received_from;
      }
    }
    leaf server-address {
      type string;
      description
        "The PCE server address";
    }
    leaf priority {
      type uint8;
      description
        "The PCE server priority";
    }
    leaf description {
      type string;
      description
        "PCEP error code";
    }
    leaf type {
      type uint8;
      description
        "PCEP error code";
    }
    leaf value {
      type uint8;
      description
        "PCEP error code";
    }
  }

  notification PCEP_SESSION_LIMIT_REACHED {
    description
      "The maximum number of 5 PCEP sessions has been reached.";
    dn-events-extensions:event-severity-level "Info";
    dn-events-extensions:event-message-string "Number of PCEP sessions has reached the system limit {max-sessions} PCEP sessions";
    dn-events-extensions:event-corrective-action-string "This is informational, no corrective action required.";
    dn-events-extensions:event-trigger-component-string "RSVP";
    dn-events-extensions:event-group "PCEP";
    leaf max-sessions {
      description
        "Session number limit";
      type enumeration {
        enum 5;
      }
    }
  }

  notification PCEP_SESSION_LIMIT_CLEARED {
    description
      "The number of concurrent PCEP sessions is below the configured maximum number of sessions.";
    dn-events-extensions:event-severity-level "Info";
    dn-events-extensions:event-message-string "Number of PCEP sessions is below the configured maximum ({max-sessions})";
    dn-events-extensions:event-corrective-action-string "This is informational, no corrective action required.";
    dn-events-extensions:event-trigger-component-string "RSVP";
    dn-events-extensions:event-group "PCEP";
    leaf max-sessions {
      description
        "Session number limit";
      type enumeration {
        enum 5;
      }
    }
  }

  notification PCEP_INTERNAL_ERROR {
    description
      "PCEP encountered an internal error.";
    dn-events-extensions:event-severity-level "Error";
    dn-events-extensions:event-message-string "PCEP process has encountered an error: {error-type}, {error-message}";
    dn-events-extensions:event-corrective-action-string "Copy the error message and contact Customer Support.";
    dn-events-extensions:event-trigger-component-string "RSVP";
    dn-events-extensions:event-group "PCEP";
    leaf error-type {
      type string;
      description
        "Error group type";
    }
    leaf error-message {
      type string;
      description
        "Error description";
    }
  }

  notification PCEP_ADMIN_STATE_CONFIG {
    description
      "The PCEP admin-state configuration has changed.";
    dn-events-extensions:event-severity-level "Info";
    dn-events-extensions:event-message-string "User {user-name} changed PCEP admin-state configuration to {new-state}";
    dn-events-extensions:event-corrective-action-string "This is informational, no corrective action required.";
    dn-events-extensions:event-trigger-component-string "Transaction-manager";
    dn-events-extensions:event-group "PCEP";
    leaf user-name {
      type string;
      description
        "User name";
    }
    leaf new-state {
      type enumeration {
        enum enabled;
        enum disabled;
      }
      description
        "Diffserv-te new admin-state";
    }
  }

  notification PCEP_SERVER_ADMIN_STATE_CONFIG {
    description
      "The PCEP server admin-state configuration has changed.";
    dn-events-extensions:event-severity-level "Info";
    dn-events-extensions:event-message-string "User {user-name} changed PCEP server {server} with priority {priority} admin-state configuration to {new-state}";
    dn-events-extensions:event-corrective-action-string "This is informational, no corrective action required.";
    dn-events-extensions:event-trigger-component-string "Transaction-manager";
    dn-events-extensions:event-group "PCEP";
    leaf user-name {
      type string;
      description
        "User name";
    }
    leaf server {
      type string;
      description
        "PCE server IP address";
    }
    leaf priority {
      type uint8;
      description
        "PCE server priority";
    }
    leaf new-state {
      type enumeration {
        enum enabled;
        enum disabled;
      }
      description
        "Diffserv-te new admin-state";
    }
  }

  notification PCEP_SERVER_CONFIG {
    description
      "The PCEP server configuration has changed.";
    dn-events-extensions:event-severity-level "Info";
    dn-events-extensions:event-message-string "User {user-name} has {action} PCEP server {server-address} configuration";
    dn-events-extensions:event-corrective-action-string "This is informational, no corrective action required.";
    dn-events-extensions:event-trigger-component-string "Transaction-manager";
    dn-events-extensions:event-group "PCEP";
    leaf user-name {
      type string;
      description
        "User name";
    }
    leaf action {
      type enumeration {
        enum added;
        enum removed;
      }
      description
        "Configuration action";
    }
    leaf server-address {
      type string;
      description
        "PCE server IP address";
    }
  }

  notification PCE_DELEGATION_STATE_CHANGE {
    description
      "The PCE server delegation state has changed.";
    dn-events-extensions:event-severity-level "Info";
    dn-events-extensions:event-message-string "PCE server {server-address} with priority {priority} delegation state change from {old-state} to {new-state}";
    dn-events-extensions:event-corrective-action-string "This is informational, no corrective action required.";
    dn-events-extensions:event-trigger-component-string "RSVP";
    dn-events-extensions:event-group "PCEP";
    leaf server-address {
      type string;
      description
        "The PCE server address";
    }
    leaf priority {
      type uint8;
      description
        "The PCE server priority";
    }
    leaf old-state {
      type enumeration {
        enum yes;
        enum no;
      }
      description
        "Old delegation state";
    }
    leaf new-state {
      type enumeration {
        enum yes;
        enum no;
      }
      description
        "New delegation state";
    }
  }

  notification SRTE_PCE_INIT_LSP_MAXIMUM_LIMIT_REACHED {
    description
      "The maximum number of PCE-initiated paths was reached.";
    dn-events-extensions:event-severity-level "Warning";
    dn-events-extensions:event-message-string "The limit of maximum PCE-initiated paths ({limit}) was reached";
    dn-events-extensions:event-corrective-action-string "Verify the PCE settings for the expected PCE initiated LSPs, and if required, increase the local PCEP maximum-initiated-policies configuration.";
    dn-events-extensions:event-trigger-component-string "Segment-Routing";
    dn-events-extensions:event-group "Segment-Routing";
    leaf limit {
      type uint16;
      description
        "The configured PCE-initiated paths limit";
    }
  }

  notification SRTE_PCE_INIT_LSP_MAXIMUM_LIMIT_CLEARED {
    description
      "The number of PCE-initiated paths is below the configured maximum limit.";
    dn-events-extensions:event-severity-level "Info";
    dn-events-extensions:event-message-string "The number of PCE-initiated is below the allowed maximum {limit}";
    dn-events-extensions:event-corrective-action-string "This is informational, no corrective action required.";
    dn-events-extensions:event-trigger-component-string "Segment-Routing";
    dn-events-extensions:event-group "Segment-Routing";
    leaf limit {
      type uint16;
      description
        "The configured PCE-initiated paths limit";
    }
  }

  notification SRTE_PCE_INIT_LSP_MAXIMUM_THRESHOLD_EXCEEDED {
    description
      "The threshold of PCE-initiated paths was reached.";
    dn-events-extensions:event-severity-level "Warning";
    dn-events-extensions:event-message-string "The threshold limit ({threshold}%) of PCE-initiated paths ({limit}) was reached, current number of PCE-initiated paths is {numeric-value}";
    dn-events-extensions:event-corrective-action-string "Verify the PCE settings for the expected PCE initiated LSPs, and if required, increase the local PCEP maximum-initiated-policies configuration.";
    dn-events-extensions:event-trigger-component-string "Segment-Routing";
    dn-events-extensions:event-group "Segment-Routing";
    leaf threshold {
      type uint8;
      description
        "Threshold percent";
    }
    leaf numeric-value {
      type uint16;
      description
        "Current number of PCE-initiated paths";
    }
    leaf limit {
      type uint16;
      description
        "The configured PCE-initiated paths limit";
    }
  }

  notification SRTE_PCE_INIT_LSP_MAXIMUM_THRESHOLD_CLEARED {
    description
      "The threshold of PCE-initiated paths was cleared.";
    dn-events-extensions:event-severity-level "Info";
    dn-events-extensions:event-message-string "The current number of PCE-initiated paths ({numeric-value}) is below the threshold limit ({threshold}%) of PCE-initiated paths ({limit}) ";
    dn-events-extensions:event-corrective-action-string "This is informational, no corrective action required.";
    dn-events-extensions:event-trigger-component-string "Segment-Routing";
    dn-events-extensions:event-group "Segment-Routing";
    leaf threshold {
      type uint8;
      description
        "Threshold percent";
    }
    leaf numeric-value {
      type uint16;
      description
        "Current number of PCE-initiated paths";
    }
    leaf limit {
      type uint16;
      description
        "The configured PCE-initiated paths limit";
    }
  }

  // BGP events

  notification BGP_IPV4_NEIGHBOR_ADJACENCY_DOWN {
    description
      "The state of the BGP neighbor has changed, the neighbor has moved from an 'up' state to a 'down' state.";
    dn-events-extensions:event-severity-level "Warning";
    dn-events-extensions:event-message-string "Instance {vrf} BGP {as-number}: Neighbor {neighbor-address} adjacency is {bgp-peer-state}, due to {reason}";
    dn-events-extensions:event-corrective-action-string "No corrective action.";
    dn-events-extensions:event-trigger-component-string "BGP";
    dn-events-extensions:event-group "BGP";
    dn-events-extensions:event-snmp-trap-name "bgpBackwardTransNotification";
    dn-events-extensions:event-snmp-trap-oid "1.3.6.1.2.1.15.0.2";
    dn-events-extensions:event-snmp-trap-vars "bgpPeerRemoteAddr.{neighbor-address} {neighbor-address} ; bgpPeerLastError.{neighbor-address} {bgp-peer-last-error} ; bgpPeerState.{neighbor-address} {bgp-peer-state}";
    leaf vrf {
      description
        "Routing instance";
      type string;
    }
    leaf as-number {
      type uint32;
      description
        "BGP AS number";
    }
    leaf neighbor-address {
      type string;
      description
        "The BGP neighbor";
    }
    leaf reason {
      type string;
      description
        "The last error seen by this peer on this connection";
    }
    leaf bgp-peer-last-error {
      type binary {
        length "2";
      }
      description
        "SNMP: The last error code and subcode seen by this
         peer on this connection.  If no error has
         occurred, this field is zero.  Otherwise, the
         first byte of this two byte OCTET STRING
         contains the error code, and the second byte
         contains the subcode.
         view: https://www.iana.org/assignments/bgp-parameters/bgp-parameters.xhtml#bgp-parameters-3";
    }
    leaf bgp-peer-state {
      type enumeration {
        enum idle {
          value 1;
        }
        enum connect {
          value 2;
        }
        enum active {
          value 3;
        }
        enum opensent {
          value 4;
        }
        enum openconfirm {
          value 5;
        }
        enum established {
          value 6;
        }
      }
      description
        "SNMP Peer State, expected value established(6)
         idle(1), connect(2), active(3), opensent(4), openconfirm(5),  established(6)";
    }
  }

  notification BGP_IPV6_NEIGHBOR_ADJACENCY_DOWN {
    description
      "The state of the BGP neighbor has changed, the neighbor has moved from an 'up' state to a 'down' state.";
    dn-events-extensions:event-severity-level "Warning";
    dn-events-extensions:event-message-string "Instance {vrf} BGP {as-number}: Neighbor {neighbor-address} adjacency is {bgp-peer-state}, due to {reason}";
    dn-events-extensions:event-corrective-action-string "No corrective action.";
    dn-events-extensions:event-trigger-component-string "BGP";
    dn-events-extensions:event-group "BGP";
    dn-events-extensions:event-snmp-trap-name "dnBgpBackwardTransition";
    dn-events-extensions:event-snmp-trap-oid "1.3.6.1.4.1.49739.2.4.0.2";
    dn-events-extensions:event-snmp-trap-vars "dnPeerLocalAddrType.0 {address-type} ; dnPeerLocalAddr.0  CONVERT inetAddr({address-type}) {local-address} ; dnPeerRemoteAddrType.0 {address-type}; dnPeerRemoteAddr.0  CONVERT inetAddr({address-type}) {neighbor-address} ; dnPeerLastErrorReceived.0 {bgp-peer-last-error} ; dnPeerState.0 {bgp-peer-state}";
    leaf vrf {
      description
        "Routing instance";
      type string;
    }
    leaf as-number {
      type uint32;
      description
        "BGP AS number";
    }
    leaf address-type {
      description
        "This object specifies the IP address type of the source IP
         address of this BFD session.  The value of unknown(0) is
         allowed only when the session is singleHop(1) and the
         source IP address of this BFD session is derived from
         the outgoing interface, or when the BFD session is not
         associated with a specific interface.  If any other
         unsupported values are attempted in a set operation, the
         agent MUST return an inconsistentValue error.";
      type enumeration {
        enum unknown {
          value 0;
        }
        enum ipv4 {
          value 1;
        }
        enum ipv6 {
          value 2;
        }
        enum dns {
          value 16;
        }
      }
    }
    leaf local-address {
      type string;
      description
        "The BGP local session address";
    }
    leaf neighbor-address {
      type string;
      description
        "The BGP neighbor";
    }
    leaf reason {
      type string;
      description
        "The last error seen by this peer on this connection.";
    }
    leaf bgp-peer-last-error {
      type binary {
        length "2";
      }
      description
        "SNMP: The last error code and subcode seen by this
         peer on this connection.  If no error has
         occurred, this field is zero.  Otherwise, the
         first byte of this two byte OCTET STRING
         contains the error code, and the second byte
         contains the subcode.
         view: https://www.iana.org/assignments/bgp-parameters/bgp-parameters.xhtml#bgp-parameters-3";
    }
    leaf bgp-peer-state {
      type enumeration {
        enum idle {
          value 1;
        }
        enum connect {
          value 2;
        }
        enum active {
          value 3;
        }
        enum opensent {
          value 4;
        }
        enum openconfirm {
          value 5;
        }
        enum established {
          value 6;
        }
      }
      description
        "SNMP Peer State, expected value established(6)
         idle(1), connect(2), active(3), opensent(4), openconfirm(5),  established(6)";
    }
  }

  notification BGP_IPV4_NEIGHBOR_ADJACENCY_BACKWARD_CHANGE {
    description
      "The state of the BGP neighbor has changed from a non-established state to a lower state. A non-established state has a state value of 5, 4, 3, 2, or 1. From high to low, the state value ranges are, established(6), openconfirm(5), opensent(4), active(3), connect(2), and idle(1). For example, if a BGP neighbor state changes from openconfirm(5) to opensent(4), this system event is triggered.";
    dn-events-extensions:event-severity-level "notice";
    dn-events-extensions:event-message-string "Instance {vrf} BGP {as-number}: Neighbor {neighbor-address} adjacency moved from {bgp-peer-old-state} to {bgp-peer-state}";
    dn-events-extensions:event-corrective-action-string "Verify that the peer configuration is the samed at both ends.";
    dn-events-extensions:event-trigger-component-string "BGP";
    dn-events-extensions:event-group "BGP";
    dn-events-extensions:event-snmp-trap-name "bgpBackwardTransNotification";
    dn-events-extensions:event-snmp-trap-oid "1.3.6.1.2.1.15.0.2";
    dn-events-extensions:event-snmp-trap-vars "bgpPeerRemoteAddr.{neighbor-address} {neighbor-address} ; bgpPeerLastError.{neighbor-address} {bgp-peer-last-error} ; bgpPeerState.{neighbor-address} {bgp-peer-state}";
    leaf vrf {
      description
        "Routing instance";
      type string;
    }
    leaf as-number {
      type uint32;
      description
        "BGP AS number";
    }
    leaf neighbor-address {
      type string;
      description
        "The BGP neighbor";
    }
    leaf bgp-peer-last-error {
      type binary {
        length "2";
      }
      description
        "SNMP: The last error code and subcode seen by this
         peer on this connection.  If no error has
         occurred, this field is zero.  Otherwise, the
         first byte of this two byte OCTET STRING
         contains the error code, and the second byte
         contains the subcode.
         view: https://www.iana.org/assignments/bgp-parameters/bgp-parameters.xhtml#bgp-parameters-3";
    }
    leaf bgp-peer-old-state {
      type enumeration {
        enum idle {
          value 1;
        }
        enum connect {
          value 2;
        }
        enum active {
          value 3;
        }
        enum opensent {
          value 4;
        }
        enum openconfirm {
          value 5;
        }
        enum established {
          value 6;
        }
      }
    }
    leaf bgp-peer-state {
      type enumeration {
        enum idle {
          value 1;
        }
        enum connect {
          value 2;
        }
        enum active {
          value 3;
        }
        enum opensent {
          value 4;
        }
        enum openconfirm {
          value 5;
        }
        enum established {
          value 6;
        }
      }
      description
        "SNMP Peer State, expected value established(6)
         idle(1), connect(2), active(3), opensent(4), openconfirm(5),  established(6)";
    }
  }

  notification BGP_IPV6_NEIGHBOR_ADJACENCY_BACKWARD_CHANGE {
    description
      "The state of the BGP neighbor has changed from a non-established state to a lower state. A non-established state has a state value of 5, 4, 3, 2, or 1. From high to low, the state value ranges are, established(6), openconfirm(5), opensent(4), active(3), connect(2), and idle(1). For example, if a BGP neighbor state changes from openconfirm(5) to opensent(4), this system event is triggered.";
    dn-events-extensions:event-severity-level "notice";
    dn-events-extensions:event-message-string "Instance {vrf} BGP {as-number}: Neighbor {neighbor-address} adjacency moved from {bgp-peer-old-state} to {bgp-peer-state}";
    dn-events-extensions:event-corrective-action-string "No corrective action.";
    dn-events-extensions:event-trigger-component-string "BGP";
    dn-events-extensions:event-group "BGP";
    dn-events-extensions:event-snmp-trap-name "dnBgpBackwardTransition";
    dn-events-extensions:event-snmp-trap-oid "1.3.6.1.4.1.49739.2.4.0.2";
    dn-events-extensions:event-snmp-trap-vars "dnPeerLocalAddrType.0 {address-type} ; dnPeerLocalAddr.0  CONVERT inetAddr({address-type}) {local-address} ; dnPeerRemoteAddrType.0 {address-type}; dnPeerRemoteAddr.0  CONVERT inetAddr({address-type}) {neighbor-address} ; dnPeerLastErrorReceived.0 {bgp-peer-last-error} ; dnPeerState.0 {bgp-peer-state}";
    leaf vrf {
      description
        "Routing instance";
      type string;
    }
    leaf as-number {
      type uint32;
      description
        "BGP AS number";
    }
    leaf address-type {
      description
        "This object specifies the IP address type of the source IP
         address of this BFD session.  The value of unknown(0) is
         allowed only when the session is singleHop(1) and the
         source IP address of this BFD session is derived from
         the outgoing interface, or when the BFD session is not
         associated with a specific interface.  If any other
         unsupported values are attempted in a set operation, the
         agent MUST return an inconsistentValue error.";
      type enumeration {
        enum unknown {
          value 0;
        }
        enum ipv4 {
          value 1;
        }
        enum ipv6 {
          value 2;
        }
        enum dns {
          value 16;
        }
      }
    }
    leaf local-address {
      type string;
      description
        "The BGP local session address";
    }
    leaf neighbor-address {
      type string;
      description
        "The BGP neighbor";
    }
    leaf bgp-peer-last-error {
      type binary {
        length "2";
      }
      description
        "SNMP: The last error code and subcode seen by this
         peer on this connection.  If no error has
         occurred, this field is zero.  Otherwise, the
         first byte of this two byte OCTET STRING
         contains the error code, and the second byte
         contains the subcode.
         view: https://www.iana.org/assignments/bgp-parameters/bgp-parameters.xhtml#bgp-parameters-3";
    }
    leaf bgp-peer-old-state {
      type enumeration {
        enum idle {
          value 1;
        }
        enum connect {
          value 2;
        }
        enum active {
          value 3;
        }
        enum opensent {
          value 4;
        }
        enum openconfirm {
          value 5;
        }
        enum established {
          value 6;
        }
      }
    }
    leaf bgp-peer-state {
      type enumeration {
        enum idle {
          value 1;
        }
        enum connect {
          value 2;
        }
        enum active {
          value 3;
        }
        enum opensent {
          value 4;
        }
        enum openconfirm {
          value 5;
        }
        enum established {
          value 6;
        }
      }
      description
        "SNMP Peer State, expected value established(6)
         idle(1), connect(2), active(3), opensent(4), openconfirm(5),  established(6)";
    }
  }

  notification BGP_IPV4_NEIGHBOR_ADJACENCY_UP {
    description
      "The state of the BGP neighbor has changed, the neighbor has moved from a 'down' state to an 'up' state.";
    dn-events-extensions:event-severity-level "Notice";
    dn-events-extensions:event-message-string "Instance {vrf} BGP {as-number}: Neighbor {neighbor-address} adjacency is up";
    dn-events-extensions:event-corrective-action-string "No corrective action.";
    dn-events-extensions:event-trigger-component-string "BGP";
    dn-events-extensions:event-group "BGP";
    dn-events-extensions:event-snmp-trap-name "bgpEstablishedNotification";
    dn-events-extensions:event-snmp-trap-oid "1.3.6.1.2.1.15.0.1";
    dn-events-extensions:event-snmp-trap-vars "bgpPeerRemoteAddr.{neighbor-address} {neighbor-address} ; bgpPeerLastError.{neighbor-address} {bgp-peer-last-error} ; bgpPeerState.{neighbor-address} {bgp-peer-state}";
    leaf vrf {
      description
        "Routing instance";
      type string;
    }
    leaf as-number {
      type uint32;
      description
        "BGP AS number";
    }
    leaf neighbor-address {
      type string;
      description
        "The BGP neighbor";
    }
    leaf bgp-peer-last-error {
      type binary {
        length "2";
      }
      description
        "SNMP: The last error code and subcode seen by this
         peer on this connection.  If no error has
         occurred, this field is zero.  Otherwise, the
         first byte of this two byte OCTET STRING
         contains the error code, and the second byte
         contains the subcode.
         view: https://www.iana.org/assignments/bgp-parameters/bgp-parameters.xhtml#bgp-parameters-3";
    }
    leaf bgp-peer-state {
      type enumeration {
        enum idle {
          value 1;
        }
        enum connect {
          value 2;
        }
        enum active {
          value 3;
        }
        enum opensent {
          value 4;
        }
        enum openconfirm {
          value 5;
        }
        enum established {
          value 6;
        }
      }
      description
        "SNMP Peer State, expected value established(6)
         idle(1), connect(2), active(3), opensent(4), openconfirm(5),  established(6)";
    }
  }

  notification BGP_IPV6_NEIGHBOR_ADJACENCY_UP {
    description
      "The state of the BGP neighbor has changed, the neighbor has moved from a 'down' state to an 'up' state.";
    dn-events-extensions:event-severity-level "Notice";
    dn-events-extensions:event-message-string "Instance {vrf} BGP {as-number}: Neighbor {neighbor-address} adjacency is up";
    dn-events-extensions:event-corrective-action-string "No corrective action.";
    dn-events-extensions:event-trigger-component-string "BGP";
    dn-events-extensions:event-group "BGP";
    dn-events-extensions:event-snmp-trap-name "dnBgpEstablished";
    dn-events-extensions:event-snmp-trap-oid "1.3.6.1.4.1.49739.2.4.0.1";
    dn-events-extensions:event-snmp-trap-vars "dnPeerLocalAddrType.0 {address-type} ; dnPeerLocalAddr.0  CONVERT inetAddr({address-type}) {local-address} ; dnPeerRemoteAddrType.0 {address-type}; dnPeerRemoteAddr.0  CONVERT inetAddr({address-type}) {neighbor-address} ; dnPeerLastErrorReceived.0 {bgp-peer-last-error} ; dnPeerState.0 {bgp-peer-state}";
    leaf vrf {
      description
        "Routing instance";
      type string;
    }
    leaf as-number {
      type uint32;
      description
        "BGP AS number";
    }
    leaf address-type {
      description
        "This object specifies the IP address type of the source IP
         address of this BFD session.  The value of unknown(0) is
         allowed only when the session is singleHop(1) and the
         source IP address of this BFD session is derived from
         the outgoing interface, or when the BFD session is not
         associated with a specific interface.  If any other
         unsupported values are attempted in a set operation, the
         agent MUST return an inconsistentValue error.";
      type enumeration {
        enum unknown {
          value 0;
        }
        enum ipv4 {
          value 1;
        }
        enum ipv6 {
          value 2;
        }
        enum dns {
          value 16;
        }
      }
    }
    leaf local-address {
      type string;
      description
        "The BGP local session address";
    }
    leaf neighbor-address {
      type string;
      description
        "The BGP neighbor";
    }
    leaf bgp-peer-last-error {
      type binary {
        length "2";
      }
      description
        "SNMP: The last error code and subcode seen by this
         peer on this connection.  If no error has
         occurred, this field is zero.  Otherwise, the
         first byte of this two byte OCTET STRING
         contains the error code, and the second byte
         contains the subcode.
         view: https://www.iana.org/assignments/bgp-parameters/bgp-parameters.xhtml#bgp-parameters-3";
    }
    leaf bgp-peer-state {
      type enumeration {
        enum idle {
          value 1;
        }
        enum connect {
          value 2;
        }
        enum active {
          value 3;
        }
        enum opensent {
          value 4;
        }
        enum openconfirm {
          value 5;
        }
        enum established {
          value 6;
        }
      }
      description
        "SNMP Peer State, expected value established(6)
         idle(1), connect(2), active(3), opensent(4), openconfirm(5),  established(6)";
    }
  }

  notification BGP_SESSION_MINIMUM_HOLD_TIME_VIOLATION {
    description
      "BGP session is rejected due to unacceptable hold time by local or remote side";
    dn-events-extensions:event-severity-level "Notice";
    dn-events-extensions:event-message-string "Instance {vrf} BGP {as-number}: Neighbor {neighbor-address} adjacency was rejected due to minimum hold-time violation."
                                            + "Received hold-time {neighbor-hold-time}, local hold-time {local-hold-time}, local minimum-hold-time {local-minimum-hold-time}";
    dn-events-extensions:event-corrective-action-string "Update hold-time settings either locally or remotely";
    dn-events-extensions:event-trigger-component-string "BGP";
    dn-events-extensions:event-group "BGP";
    leaf vrf {
      description
        "Routing instance";
      type string;
    }
    leaf as-number {
      type uint32;
      description
        "BGP AS number";
    }
    leaf neighbor-address {
      type string;
      description
        "The BGP neighbor";
    }
    leaf neighbor-hold-time {
      description
        "Neighbor hold time as received in open message";
      type uint16;
    }
    leaf local-hold-time {
      description
        "Local hold time as sent in open message";
      type uint16;
    }
    leaf local-minimum-hold-time {
      description
        "Local minimum hold-time value";
      type uint16;
    }
  }

  notification BGP_NEIGHBOR_MAXIMUM_PREFIX_LIMIT_REACHED {
    description
      "The maximum number of prefixes learned via BGP for each BGP neighbor address family has been reached. This will cause an exceed action to be triggered, either a warning only or the session is restarted.";
    dn-events-extensions:event-severity-level "Warning";
    dn-events-extensions:event-message-string "Instance {vrf} BGP {as-number}: Exceeded maximum prefix learned from BGP neighbor {neighbor-address} for address family {address-family}. Resulting in an exceed action {exceed-action}";
    dn-events-extensions:event-corrective-action-string "No corrective action.";
    dn-events-extensions:event-trigger-component-string "BGP";
    dn-events-extensions:event-group "BGP";
    leaf vrf {
      description
        "Routing instance";
      type string;
    }
    leaf as-number {
      type uint32;
      description
        "BGP AS number";
    }
    leaf neighbor-address {
      type string;
      description
        "The BGP neighbor address";
    }
    leaf address-family {
      type string;
      description
        "BGP afi-safi type";
    }
    leaf exceed-action {
      type enumeration {
        enum Warning-Only;
        enum Restart-session;
        enum Excess-discard;
      }
    }
  }

  notification BGP_NEIGHBOR_MAXIMUM_PREFIX_LIMIT_CLEARED {
    description
      "The maximum number of prefixes learned via BGP for each BGP neighbor address family has been reached. This will cause an exceed action to be triggered, either a warning only or the session is restarted.";
    dn-events-extensions:event-severity-level "Info";
    dn-events-extensions:event-message-string "Instance {vrf} BGP {as-number}: Total number of prefixes is below maximum prefix allowed from BGP neighbor {neighbor-address} for address family {address-family}.";
    dn-events-extensions:event-corrective-action-string "No corrective action.";
    dn-events-extensions:event-trigger-component-string "BGP";
    dn-events-extensions:event-group "BGP";
    leaf vrf {
      description
        "Routing instance";
      type string;
    }
    leaf as-number {
      type uint32;
      description
        "BGP AS number";
    }
    leaf neighbor-address {
      type string;
      description
        "The BGP neighbor address";
    }
    leaf address-family {
      type string;
      description
        "BGP afi-safi type";
    }
  }

  notification BGP_NEIGHBOR_MAXIMUM_PREFIX_LIMIT_EXCESS_DISCARD_RECOVER_REQUIRED {
    description
      "The number of prefixes learned from the BGP neighbor address family is below the configured limit. The system cannot automatically recover the discarded routes, and user intervention is needed.";
    dn-events-extensions:event-severity-level "Notice";
    dn-events-extensions:event-message-string "Instance {vrf} BGP {as-number}: Total number of prefixes is below maximum prefix allowed from BGP neighbor {neighbor-address} for address family {address-family}, discarded paths cannot be recovered, consider resetting the neighbor session to retrieve all required paths.";
    dn-events-extensions:event-corrective-action-string "Reset the BGP peering session for the neighbor routes to be relearned.";
    dn-events-extensions:event-trigger-component-string "BGP";
    dn-events-extensions:event-group "BGP";
    leaf vrf {
      description
        "Routing instance";
      type string;
    }
    leaf as-number {
      type uint32;
      description
        "BGP AS number";
    }
    leaf neighbor-address {
      type string;
      description
        "The BGP neighbor address";
    }
    leaf address-family {
      type string;
      description
        "BGP afi-safi type";
    }
  }

  notification BGP_NEIGHBOR_MAXIMUM_PREFIX_THRESHOLD_EXCEEDED {
    description
      "The number of prefixes learned via BGP has crossed the configured threshold for the IPv4 or IPv6 address family.";
    dn-events-extensions:event-severity-level "Notice";
    dn-events-extensions:event-message-string "Instance {vrf} BGP {as-number}: Exceeded configured maximum prefix {max-prefix} threshold of {threshold}%. {num-of-prefix} prefixes learned from BGP neighbor {neighbor-address} for address family {address-family}.";
    dn-events-extensions:event-corrective-action-string "No corrective action.";
    dn-events-extensions:event-trigger-component-string "BGP";
    dn-events-extensions:event-group "BGP";
    dn-events-extensions:event-snmp-trap-name "dnBgpNeighborMaximumPrefixThresholdExceeded";
    dn-events-extensions:event-snmp-trap-oid "1.3.6.1.4.1.49739.2.4.0.3";
    dn-events-extensions:event-snmp-trap-vars
      "dnPeerLocalAddrType.0 {address-type} ; dnPeerLocalAddr.0  CONVERT inetAddr({address-type}) {local-address} ;
       dnPeerRemoteAddrType.0 {address-type}; dnPeerRemoteAddr.0  CONVERT inetAddr({address-type}) {neighbor-address} ;
       dnPeerAfi.0 {afi}; dnPeerSafi.0 {sub-address-family};
       dnPeerAfiSafiMaxPrefix.0 {max-prefix} ; dnPeerAfiSafiThreshold.0 {threshold};
       dnPeerAfiSafiMaxReceivedPrefix.0 {num-of-prefix}";
    leaf vrf {
      description
        "Routing instance";
      type string;
    }
    leaf as-number {
      type uint32;
      description
        "BGP AS number";
    }
    leaf max-prefix {
      type uint32;
      description
        "Configured maximum-prefix";
    }
    leaf threshold {
      type uint8;
      description
        "Configured maximum-prefix threshold";
    }
    leaf num-of-prefix {
      type uint32;
      description
        "Number of prefixes learned";
    }
    leaf neighbor-address {
      type string;
      description
        "The BGP neighbor address";
    }
    leaf address-family {
      type string;
      description
        "BGP afi-safi type";
    }
    leaf address-type {
      description
        "This object specifies the IP address type of the source IP
         address of this BFD session.  The value of unknown(0) is
         allowed only when the session is singleHop(1) and the
         source IP address of this BFD session is derived from
         the outgoing interface, or when the BFD session is not
         associated with a specific interface.  If any other
         unsupported values are attempted in a set operation, the
         agent MUST return an inconsistentValue error.";
      type enumeration {
        enum unknown {
          value 0;
        }
        enum ipv4 {
          value 1;
        }
        enum ipv6 {
          value 2;
        }
        enum dns {
          value 16;
        }
      }
    }
    leaf local-address {
      type string;
      description
        "The BGP local session address";
    }
    leaf afi {
      description
        "This object specifies the address-family type with bgp neighbor";
      type enumeration {
        enum unknown {
          value 0;
        }
        enum ipv4 {
          value 1;
        }
        enum ipv6 {
          value 2;
        }
        enum dns {
          value 16;
        }
        enum l2vpn {
          value 25;
        }
        enum link-state {
          value 16388;
        }
      }
    }
    leaf sub-address-family {
      description
        "This object specifies the sub-address-family type with bgp neighbor";
      type enumeration {
        enum unicast {
          value 1;
        }
        enum multicast {
          value 2;
        }
        enum unicastAndMulticast {
          value 3;
        }
        enum labeledUnicast {
          value 4;
        }
        enum vpls {
          value 65;
        }
        enum evpn {
          value 70;
        }
        enum link-state {
          value 71;
        }
        enum vpn {
          value 128;
        }
        enum rt-constrains {
          value 132;
        }
        enum flowspec {
          value 133;
        }
        enum flowspecVpn {
          value 134;
        }
      }
    }
  }

  notification BGP_NEIGHBOR_MAXIMUM_PREFIX_THRESHOLD_CLEARED {
    description
      "The number of prefixes learned via BGP is below the configured threshold for the IPv4 or IPv6 address family.";
    dn-events-extensions:event-severity-level "Info";
    dn-events-extensions:event-message-string "Instance {vrf} BGP {as-number}: Total number of prefixes is below the threshold of {threshold}%. {num-of-prefix} prefixes learned from BGP neighbor {neighbor-address} for address family {address-family}.";
    dn-events-extensions:event-corrective-action-string "This is informational, no corrective action required.";
    dn-events-extensions:event-trigger-component-string "BGP";
    dn-events-extensions:event-group "BGP";
    dn-events-extensions:event-snmp-trap-name "dnBgpNeighborMaximumPrefixThresholdCleared";
    dn-events-extensions:event-snmp-trap-oid "1.3.6.1.4.1.49739.2.4.0.4";
    dn-events-extensions:event-snmp-trap-vars
      "dnPeerLocalAddrType.0 {address-type} ; dnPeerLocalAddr.0  CONVERT inetAddr({address-type}) {local-address} ;
       dnPeerRemoteAddrType.0 {address-type}; dnPeerRemoteAddr.0  CONVERT inetAddr({address-type}) {neighbor-address} ;
       dnPeerAfi.0 {afi}; dnPeerSafi.0 {sub-address-family};
       dnPeerAfiSafiThreshold.0 {threshold};
       dnPeerAfiSafiMaxReceivedPrefix.0 {num-of-prefix}";
    leaf vrf {
      description
        "Routing instance";
      type string;
    }
    leaf as-number {
      type uint32;
      description
        "BGP AS number";
    }
    leaf max-prefix {
      type uint32;
      description
        "Configured maximum-prefix";
    }
    leaf threshold {
      type uint8;
      description
        "Configured maximum-prefix threshold";
    }
    leaf num-of-prefix {
      type uint32;
      description
        "Number of prefixes learned";
    }
    leaf neighbor-address {
      type string;
      description
        "The BGP neighbor address";
    }
    leaf address-family {
      type string;
      description
        "BGP afi-safi type";
    }
    leaf address-type {
      description
        "This object specifies the IP address type of the source IP
         address of this BFD session.  The value of unknown(0) is
         allowed only when the session is singleHop(1) and the
         source IP address of this BFD session is derived from
         the outgoing interface, or when the BFD session is not
         associated with a specific interface.  If any other
         unsupported values are attempted in a set operation, the
         agent MUST return an inconsistentValue error.";
      type enumeration {
        enum unknown {
          value 0;
        }
        enum ipv4 {
          value 1;
        }
        enum ipv6 {
          value 2;
        }
        enum dns {
          value 16;
        }
      }
    }
    leaf local-address {
      type string;
      description
        "The BGP local session address";
    }
    leaf afi {
      description
        "This object specifies the address-family type with bgp neighbor";
      type enumeration {
        enum unknown {
          value 0;
        }
        enum ipv4 {
          value 1;
        }
        enum ipv6 {
          value 2;
        }
        enum dns {
          value 16;
        }
        enum l2vpn {
          value 25;
        }
        enum link-state {
          value 16388;
        }
      }
    }
    leaf sub-address-family {
      description
        "This object specifies the sub-address-family type with bgp neighbor";
      type enumeration {
        enum unicast {
          value 1;
        }
        enum multicast {
          value 2;
        }
        enum unicastAndMulticast {
          value 3;
        }
        enum labeledUnicast {
          value 4;
        }
        enum vpls {
          value 65;
        }
        enum evpn {
          value 70;
        }
        enum link-state {
          value 71;
        }
        enum vpn {
          value 128;
        }
        enum rt-constrains {
          value 132;
        }
        enum flowspec {
          value 133;
        }
        enum flowspecVpn {
          value 134;
        }
      }
    }
  }

  notification BGP_MAXIMUM_SESSIONS_LIMIT_REACHED {
    description
      "The number of BGP sessions has reached the configured system limit.";
    dn-events-extensions:event-severity-level "Warning";
    dn-events-extensions:event-message-string "Number of BGP sessions has reached system limit of {limit}";
    dn-events-extensions:event-corrective-action-string "No corrective action.";
    dn-events-extensions:event-trigger-component-string "BGP";
    dn-events-extensions:event-group "BGP";
    leaf limit {
      type uint16;
      description
        "The accumulated BGP sessions on all vrf instances";
    }
  }

  notification BGP_MAXIMUM_SESSIONS_LIMIT_CLEARED {
    description
      "BGP sessions have been removed, the number of BGP sessions is below the system limit.";
    dn-events-extensions:event-severity-level "Info";
    dn-events-extensions:event-message-string "Number of BGP sessions is below the system limit of {limit} adjacencies";
    dn-events-extensions:event-corrective-action-string "This is informational, no corrective action required.";
    dn-events-extensions:event-trigger-component-string "BGP";
    dn-events-extensions:event-group "BGP";
    leaf limit {
      type uint16;
      description
        "The accumulated BGP sessions on all VRF instances";
    }
  }

  notification BGP_MAXIMUM_SESSIONS_THRESHOLD_EXCEEDED {
    description
      "The number of BGP sessions has crossed the system threshold.";
    dn-events-extensions:event-severity-level "Notice";
    dn-events-extensions:event-message-string "Number of BGP sessions has crossed the system threshold {threshold}% limit of {limit}, the number of BGP sessions ({numeric-value})";
    dn-events-extensions:event-corrective-action-string "No corrective action.";
    dn-events-extensions:event-trigger-component-string "BGP";
    dn-events-extensions:event-group "BGP";
    leaf threshold {
      type uint8;
      description
        "Threshold percent";
    }
    leaf numeric-value {
      type uint16;
      description
        "Current number of BGP sessions";
    }
    leaf limit {
      type uint16;
      description
        "The accumulated BGP sessions on all VRF instances";
    }
  }

  notification BGP_MAXIMUM_SESSIONS_THRESHOLD_CLEARED {
    description
      "The number of BGP sessions is below the system threshold.";
    dn-events-extensions:event-severity-level "Info";
    dn-events-extensions:event-message-string "Number of BGP sessions is below the system threshold {threshold}% of the limit ({limit}), the current number of BGP sessions is ({numeric-value})";
    dn-events-extensions:event-corrective-action-string "This is informational, no corrective action required.";
    dn-events-extensions:event-trigger-component-string "BGP";
    dn-events-extensions:event-group "BGP";
    leaf threshold {
      type uint8;
      description
        "Threshold percent";
    }
    leaf numeric-value {
      type uint16;
      description
        "Current number of BGP neighbors";
    }
    leaf limit {
      type uint16;
      description
        "The accumulated BGP sessions on all VRF instances";
    }
  }

  notification BGP_VRF_IPV4_MAXIMUM_ROUTES_LIMIT_REACHED {
    description
      "The number of BGP routes in a given VRF IPv4 unicast table has reached the configured system limit.";
    dn-events-extensions:event-severity-level "Warning";
    dn-events-extensions:event-message-string "Instance {vrf} BGP {as-number}: Number of BGP ipv4-unicast routes has reached system table limit of {limit}";
    dn-events-extensions:event-corrective-action-string "Verify that in-bound policy filtering is in use to accept only desired routes.";
    dn-events-extensions:event-trigger-component-string "BGP";
    dn-events-extensions:event-group "BGP";
    leaf vrf {
      description
        "Routing instance";
      type string;
    }
    leaf as-number {
      type uint32;
      description
        "BGP AS number";
    }
    leaf limit {
      type uint32;
      description
        "BGP route table limit";
    }
  }

  notification BGP_VRF_IPV6_MAXIMUM_ROUTES_LIMIT_REACHED {
    description
      "The number of BGP routes in a given VRF IPv6 unicast table has reached the configured system limit.";
    dn-events-extensions:event-severity-level "Warning";
    dn-events-extensions:event-message-string "Instance {vrf} BGP {as-number}: Number of BGP ipv6-unicast routes has reached system table limit of {limit}";
    dn-events-extensions:event-corrective-action-string "Verify that in-bound policy filtering is in use to accept only desired routes.";
    dn-events-extensions:event-trigger-component-string "BGP";
    dn-events-extensions:event-group "BGP";
    leaf vrf {
      description
        "Routing instance";
      type string;
    }
    leaf as-number {
      type uint32;
      description
        "BGP AS number";
    }
    leaf limit {
      type uint32;
      description
        "BGP route table limit";
    }
  }

  notification BGP_VRF_IPV4_MAXIMUM_ROUTES_LIMIT_CLEARED {
    description
      "The number of BGP routes in a given VRF IPv4 unicast table is below the system limit.";
    dn-events-extensions:event-severity-level "Info";
    dn-events-extensions:event-message-string "Instance {vrf} BGP {as-number}: Number of BGP ipv4-unicast routes is below 90% of the system limit of {limit}. Pending over-limit routes will now be processed";
    dn-events-extensions:event-corrective-action-string "This is informational, no corrective action required.";
    dn-events-extensions:event-trigger-component-string "BGP";
    dn-events-extensions:event-group "BGP";
    leaf vrf {
      description
        "Routing instance";
      type string;
    }
    leaf as-number {
      type uint32;
      description
        "BGP AS number";
    }
    leaf limit {
      type uint32;
      description
        "BGP route table limit";
    }
  }

  notification BGP_VRF_IPV6_MAXIMUM_ROUTES_LIMIT_CLEARED {
    description
      "The number of BGP routes in a given VRF IPv6 unicast table is below the system limit.";
    dn-events-extensions:event-severity-level "Info";
    dn-events-extensions:event-message-string "Instance {vrf} BGP {as-number}: Number of BGP ipv6-unicast routes is below 90% of the system limit of {limit}. Pending over-limit routes will now be processed";
    dn-events-extensions:event-corrective-action-string "This is informational, no corrective action required.";
    dn-events-extensions:event-trigger-component-string "BGP";
    dn-events-extensions:event-group "BGP";
    leaf vrf {
      description
        "Routing instance";
      type string;
    }
    leaf as-number {
      type uint32;
      description
        "BGP AS number";
    }
    leaf limit {
      type uint32;
      description
        "BGP route table limit";
    }
  }

  notification BGP_UPDATE_EXCEED_MAX_SIZE {
    description
      "The size of a locally generated update message exceeds the maximum BGP message size of 4096 bytes.";
    dn-events-extensions:event-severity-level "Notice";
    dn-events-extensions:event-message-string "Instance {vrf} BGP {as-number}: An expected adj-out update for {afi-safi} exceed bgp message maximum. Update message expected size {msg-total-size}, nlri value {value} and size {nlri-size}, attributes size {attr-size}";
    dn-events-extensions:event-corrective-action-string "Check if the prefix attributes exceed the maximum size.";
    dn-events-extensions:event-trigger-component-string "BGP";
    dn-events-extensions:event-group "BGP";
    leaf vrf {
      description
        "Routing instance";
      type string;
    }
    leaf as-number {
      type uint32;
      description
        "BGP AS number";
    }
    leaf afi-safi {
      type string;
      description
        "nlri <address-family>-<sub-address-family>";
    }
    leaf msg-total-size {
      type uint32;
      description
        "bgp msg size in bytes";
    }
    leaf value {
      type string;
      description
        "nlri value";
    }
    leaf nlri-size {
      type uint32;
      description
        "nlri size in bytes";
    }
    leaf attr-size {
      type uint32;
      description
        "attributes size in bytes";
    }
  }

  notification BGP_ATTRIBUTE_EXCEED_MAX_SIZE {
    description
      "The size of an attribute update exceeds the maximum BGP attribute list size.";
    dn-events-extensions:event-severity-level "Notice";
    dn-events-extensions:event-message-string "Instance {vrf} BGP {as-number}: An expected adj-out update for {afi-safi} has attribute {attribute-name} that exceed attribute size. Attributes size {attr-size}";
    dn-events-extensions:event-corrective-action-string "Check for routing loops where attributes may infinitely increase.";
    dn-events-extensions:event-trigger-component-string "BGP";
    dn-events-extensions:event-group "BGP";
    leaf vrf {
      description
        "Routing instance";
      type string;
    }
    leaf as-number {
      type uint32;
      description
        "BGP AS number";
    }
    leaf afi-safi {
      type string;
      description
        "nlri <address-family>-<sub-address-family>";
    }
    leaf attribute-name {
      type string;
      description
        "nlri attribute name";
    }
    leaf attr-size {
      type uint32;
      description
        "attributes size in bytes";
    }
  }

  notification BGP_MALFORM_UPDATE {
    description
      "This event indicates that an UPDATE message contains one or more malformed NLRI or attributes was received. The action taken depends on the severity of the error.";
    dn-events-extensions:event-severity-level "Error";
    dn-events-extensions:event-message-string "Malformed update {malform-type} {malformed-field} was received from neighbor {neighbor-address} on vrf {vrf-name}. Action taken {action-description}. {error-description}";
    dn-events-extensions:event-corrective-action-string "Check BGP neighbor configuration and message compatibility.";
    dn-events-extensions:event-trigger-component-string "BGP";
    dn-events-extensions:event-group "BGP";
    leaf malform-type {
      type enumeration {
        enum nlri {
          description
            "Malformed NLRI";
        }
        enum attribute {
          description
            "Malformed attribute";
        }
      }
      description
        "The type of malformed data: nlri or attribute";
    }
    leaf malformed-field {
      type string;
      description
        "The malformed attribute or NLRI field name";
    }
    leaf neighbor-address {
      type string;
      description
        "The BGP neighbor address";
    }
    leaf vrf-name {
      type string;
      description
        "The VRF name";
    }
    leaf action-description {
      type string;
      description
        "Action taken following the receipt of the malformed update, e.g. treat as withdraw, attr discard, etc.";
    }
    leaf error-description {
      type string;
      description
        "Optional error description";
    }
  }

  notification BGP_INTERNAL_ERROR {
    description
      "The BGP process has failed due to an internal error.";
    dn-events-extensions:event-severity-level "Error";
    dn-events-extensions:event-message-string "BGP process has encountered an error: {error-type}, {error-message}";
    dn-events-extensions:event-corrective-action-string "Copy the error message and contact Customer Support.";
    dn-events-extensions:event-trigger-component-string "BGP";
    dn-events-extensions:event-group "BGP";
    leaf error-type {
      type string;
      description
        "Error group type";
    }
    leaf error-message {
      type string;
      description
        "Error description";
    }
  }

  notification BGP_SR_RECEIVED_INVALID_PREFIX_SID {
    description
      "BGP best path for a learned route include invalid prefix-sid attribute";
    dn-events-extensions:event-severity-level "Warning";
    dn-events-extensions:event-message-string "Instance {vrf} BGP {as-number}: received invalid SR Prefix-SID from neighbor {neighbor-address} for route {ip-prefix}. Invalid reason: {reason}";
    dn-events-extensions:event-corrective-action-string "Check configuration on advertising route origin";
    dn-events-extensions:event-trigger-component-string "BGP";
    dn-events-extensions:event-group "BGP";
    leaf vrf {
      description
        "Routing instance";
      type string;
    }
    leaf as-number {
      type uint32;
      description
        "BGP AS number";
    }
    leaf neighbor-address {
      type string;
      description
        "The BGP neighbor address";
    }
    leaf ip-prefix {
      type string;
      description
        "BGP learned route";
    }
    leaf reason {
      description
        "Reason string describing problem with received prefix-sid attribute";
      type string;
    }
  }

  notification BGP_SR_CONFLICTING_PREFIX_SID_SAME_PREFIX {
    description
      "BGP recevied different prefix-sid of same prefix on different paths. Label allocation will be per best path";
    dn-events-extensions:event-severity-level "Notice";
    dn-events-extensions:event-message-string "Instance {vrf} BGP {as-number}: received conflicting Prefix-SID attribute for prefix {ip-prefix} on different paths. Best-path attribute: {attribute}. Label allocation will be according to best-path";
    dn-events-extensions:event-corrective-action-string "Check configuration on advertising route origin";
    dn-events-extensions:event-trigger-component-string "BGP";
    dn-events-extensions:event-group "BGP";
    leaf vrf {
      description
        "Routing instance";
      type string;
    }
    leaf as-number {
      type uint32;
      description
        "BGP AS number";
    }
    leaf ip-prefix {
      type string;
      description
        "BGP learned route";
    }
    leaf attribute {
      description
        "Prefix SID attribute information, including index and originator srgb";
      type string;
    }
  }

  notification BGP_SR_CONFCLITING_PREFIX_SAME_LABEL_INDEX {
    description
      "BGP best path for a learned route is in conflicting prefix-sid situation, preventing label allocation per segment-routing logic";
    dn-events-extensions:event-severity-level "Warning";
    dn-events-extensions:event-message-string "Instance {vrf} BGP {as-number}: Allocated dynamic labeled-unicast label for {ip-prefix} instead of Prefix-SID label due to conflicting Label-Index. Conflicted SID index {index-value}. ";
    dn-events-extensions:event-corrective-action-string "Check configuration on advertising route origin";
    dn-events-extensions:event-trigger-component-string "BGP";
    dn-events-extensions:event-group "BGP";
    leaf vrf {
      description
        "Routing instance";
      type string;
    }
    leaf as-number {
      type uint32;
      description
        "BGP AS number";
    }
    leaf ip-prefix {
      type string;
      description
        "the prefix for which dynamic labeled-unicast label is allocated instead of Prefix-SID label";
    }
    leaf index-value {
      description
        "The SID index value which was learned for different prefixes thus resulting in conflicting state";
      type uint32;
    }
  }

  // BGP NSR events

  notification BGP_NSR_CONFIG {
    description
      "The BGP NSR (Non-Stop Routing) admin-state configuration was changed by the user listed.";
    dn-events-extensions:event-severity-level "Info";
    dn-events-extensions:event-message-string "User {user-name} has changed BGP NSR admin-state configuration to {new-state}";
    dn-events-extensions:event-corrective-action-string "This is informational, no corrective action required.";
    dn-events-extensions:event-trigger-component-string "bgp";
    dn-events-extensions:event-group "BGP";
    leaf user-name {
      type string;
      description
        "Username";
    }
    leaf new-state {
      type enumeration {
        enum enabled;
        enum disabled;
      }
      description
        "BGP NSR admin-state";
    }
  }

  notification BGP_NSR_RECOVERED {
    description
      "The system has performed a BGP Non-Stop Routing recovery due to a restart of the bgpd process.";
    dn-events-extensions:event-severity-level "Notice";
    dn-events-extensions:event-message-string "BGP Non-Stop Routing recovery was performed due to a restart of the bgpd process";
    dn-events-extensions:event-corrective-action-string "This is informational, no corrective action required.";
    dn-events-extensions:event-trigger-component-string "bgp";
    dn-events-extensions:event-group "BGP";
  }

  notification BGP_NSR_RECOVERY_FAILED {
    description
      "The BGP process failed to recover in Non-Stop Routing mode.";
    dn-events-extensions:event-severity-level "Warning";
    dn-events-extensions:event-message-string "BGP process failed to recover in Non-Stop Routing mode";
    dn-events-extensions:event-corrective-action-string "Verify NSR readiness prior to the failure event.";
    dn-events-extensions:event-trigger-component-string "bgp";
    dn-events-extensions:event-group "BGP";
  }

  notification BGP_NSR_DB_NOT_SYNC {
    description
      "The standby NCC BGP NSR database is not synchronized. BGP will not recover in Non-Stop Routing mode if a system switchover occurs.";
    dn-events-extensions:event-severity-level "Warning";
    dn-events-extensions:event-message-string "Standby NCC BGP NSR database is not synchronized. BGP will not recover in Non-Stop Routing mode if a system switchover occurs";
    dn-events-extensions:event-corrective-action-string "Verify connectivity to the standby NCC.";
    dn-events-extensions:event-trigger-component-string "bgp";
    dn-events-extensions:event-group "BGP";
  }

  notification BGP_NSR_DB_SYNC {
    description
      "The standby NCC BGP NSR database is synchronized.";
    dn-events-extensions:event-severity-level "Info";
    dn-events-extensions:event-message-string "Standby NCC BGP NSR database is synchronized";
    dn-events-extensions:event-corrective-action-string "This is informational, no corrective action required.";
    dn-events-extensions:event-trigger-component-string "bgp";
    dn-events-extensions:event-group "BGP";
  }

  // BGP RPKI events

  notification BGP_RPKI_SERVER_SESSION_UP {
    description
      "The RTR session with RPKI cache-server has been established.";
    dn-events-extensions:event-severity-level "Info";
    dn-events-extensions:event-message-string "RTR session with RPKI cache-server {rpki-server-address}:{rpki-server-port} is up.";
    dn-events-extensions:event-corrective-action-string "This is informational, no corrective action required.";
    dn-events-extensions:event-trigger-component-string "BGP";
    dn-events-extensions:event-group "BGP";
    leaf rpki-server-address {
      type string;
      description
        "The RPKI cache-server's IP address or hostname";
    }
    leaf rpki-server-port {
      type uint16;
      description
        "The RPKI server's RTR session port";
    }
  }

  notification BGP_RPKI_SERVER_SESSION_DOWN {
    description
      "The RTR session with RPKI cache-server has been terminated.";
    dn-events-extensions:event-severity-level "Info";
    dn-events-extensions:event-message-string "RTR session with RPKI cache-server {rpki-server-address}:{rpki-server-port} is down. Down reason: {down-reason}.";
    dn-events-extensions:event-corrective-action-string "This is informational, no corrective action required.";
    dn-events-extensions:event-trigger-component-string "BGP";
    dn-events-extensions:event-group "BGP";
    leaf rpki-server-address {
      type string;
      description
        "The RPKI cache-server's IP address or hostname";
    }
    leaf rpki-server-port {
      type uint16;
      description
        "The RPKI server's RTR session port";
    }
    leaf down-reason {
      type string;
      description
        "Down reason for the session with the RPKI cache server";
    }
  }

  // Routing Manager Events

  notification ROUTING_MANAGER_INTERNAL_ERROR {
    description
      "The Routing Manager process has encountered an internal error.";
    dn-events-extensions:event-severity-level "Error";
    dn-events-extensions:event-message-string "routing_manager process has encountered an error: {error-type}, {error-message}";
    dn-events-extensions:event-corrective-action-string "Copy the error message and contact Customer Support.";
    dn-events-extensions:event-trigger-component-string "ROUTING_MANAGER";
    dn-events-extensions:event-group "System";
    leaf error-type {
      type string;
      description
        "Error group type";
    }
    leaf error-message {
      type string;
      description
        "Error description";
    }
  }

  // Multicast Events

  notification MULTICAST_MAXIMUM_NCP_SG_REPLICATIONS_LIMIT_REACHED {
    description
      "The number of multicast (S,G) replications has reached the configured system limit per NCP.";
    dn-events-extensions:event-severity-level "Warning";
    dn-events-extensions:event-message-string "Number of multicast (S,G) replications on NCP {ncp-id} has reached the system limit of {limit} replications per NCP";
    dn-events-extensions:event-corrective-action-string "Review the multicast configuration in the network.";
    dn-events-extensions:event-trigger-component-string "WB Agent";
    dn-events-extensions:event-group "Multicast";
    leaf limit {
      type uint32;
      description
        "The maximum limit number of multicast (S,G) replications";
    }
    leaf ncp-id {
      type uint16;
      description
        "NCP ID";
    }
  }

  notification MULTICAST_MAXIMUM_NCP_SG_REPLICATIONS_LIMIT_CLEARED {
    description
      "The number of multicast (S,G) replications has moved below the system limit per NCP.";
    dn-events-extensions:event-severity-level "Info";
    dn-events-extensions:event-message-string "Number of multicast (S,G) replications on NCP {ncp-id} has moved below the system limit of {limit} replications per NCP";
    dn-events-extensions:event-corrective-action-string "This is informational, no corrective action required.";
    dn-events-extensions:event-trigger-component-string "WB Agent";
    dn-events-extensions:event-group "Multicast";
    leaf limit {
      type uint32;
      description
        "The maximum limit of multicast (S,G) replications";
    }
    leaf ncp-id {
      type uint16;
      description
        "NCP ID";
    }
  }

  notification MULTICAST_MAXIMUM_NCP_SG_REPLICATIONS_THRESHOLD_EXCEEDED {
    description
      "The number of multicast (S,G) replications had crossed the system threshold per NCP.";
    dn-events-extensions:event-severity-level "Notice";
    dn-events-extensions:event-message-string "Number of multicast (S,G) replications on NCP {ncp-id} has crossed the {threshold}% system threshold of the maximum limit of {limit} replications per NCP. The current number of multicast (S,G) replications is {current-sg-replications}";
    dn-events-extensions:event-corrective-action-string "No corrective action.";
    dn-events-extensions:event-trigger-component-string "WB Agent";
    dn-events-extensions:event-group "Multicast";
    leaf threshold {
      type uint8;
      description
        "Threshold percent";
    }
    leaf limit {
      type uint32;
      description
        "The limit of multicast (S,G) replications";
    }
    leaf current-sg-replications {
      type uint32;
      description
        "The current multicast (S,G) replications";
    }
    leaf ncp-id {
      type uint16;
      description
        "NCP ID";
    }
  }

  notification MULTICAST_MAXIMUM_NCP_SG_REPLICATIONS_THRESHOLD_CLEARED {
    description
      "The number of multicast (S,G) replications has moved below the system threshold per NCP.";
    dn-events-extensions:event-severity-level "Info";
    dn-events-extensions:event-message-string "Number of multicast (S,G) replications on NCP {ncp-id} has moved below the {threshold}% system threshold of the maximum limit of {limit} replications per NCP. The current number of multicast (S,G) replications is {current-sg-replications}";
    dn-events-extensions:event-corrective-action-string "This is informational, no corrective action required.";
    dn-events-extensions:event-trigger-component-string "WB Agent";
    dn-events-extensions:event-group "Multicast";
    leaf threshold {
      type uint8;
      description
        "Threshold percent";
    }
    leaf limit {
      type uint32;
      description
        "The limit of multicast (S,G) replications.";
    }
    leaf current-sg-replications {
      type uint32;
      description
        "The current multicast (S,G) replications.";
    }
    leaf ncp-id {
      type uint16;
      description
        "NCP ID";
    }
  }

  // PIM Events

  notification PIM_NEIGHBOR_UP {
    description
      "The PIM neighbor adjacency has moved to an 'up' state.";
    dn-events-extensions:event-severity-level "Info";
    dn-events-extensions:event-message-string "PIM neighbor {neighbor-ip-address} moved to an up state, on interface {if-name}. VRF instance {vrf-name}";
    dn-events-extensions:event-corrective-action-string "This is informational, no corrective action required.";
    dn-events-extensions:event-trigger-component-string "PIM";
    dn-events-extensions:event-group "PIM";
    dn-events-extensions:event-snmp-trap-name "dnPimNeighborUp";
    dn-events-extensions:event-snmp-trap-oid "1.3.6.1.4.1.49739.2.5.0.1";
    dn-events-extensions:event-snmp-trap-vars "dnPimNeighborAddress.0 CONVERT inetAddr({address-type}) {neighbor-ip-address}";
    leaf address-type {
      type enumeration {
        enum unknown {
          value 0;
        }
        enum ipv4 {
          value 1;
        }
        enum ipv6 {
          value 2;
        }
      }
      description
        "A value that represents a type of internet address.
         SYNTAX INTEGER  unknown(0), ipv4(1), ipv6(2), ipv4z(3), ipv6z(4), dns(16)";
    }
    leaf neighbor-ip-address {
      type string;
      description
        "Neighbor IP address";
    }
    leaf if-name {
      type string;
      description
        "Interface name";
    }
    leaf vrf-name {
      description
        "the vrf in which event happened";
      type string;
    }
  }

  notification PIM_NEIGHBOR_DOWN {
    description
      "The PIM neighbor adjacency moved to a 'down' state. This notification is generated when the neighbor hold-timer expires.";
    dn-events-extensions:event-severity-level "Warning";
    dn-events-extensions:event-message-string "PIM neighbor {neighbor-ip-address} adjacency lost on interface {if-name} due to {reason}. Uptime {neighbor-uptime}. VRF instance {vrf-name}";
    dn-events-extensions:event-corrective-action-string "No corrective action.";
    dn-events-extensions:event-trigger-component-string "PIM";
    dn-events-extensions:event-group "PIM";
    dn-events-extensions:event-snmp-trap-name "pimNeighborLoss";
    dn-events-extensions:event-snmp-trap-oid "1.3.6.1.2.1.157.0.1";
    dn-events-extensions:event-snmp-trap-vars "pimNeighborUpTime {neighbor-uptime-snmp} ; dnPimInterfaceName.0 {if-name} ; dnPimNeighborAddress.0 CONVERT inetAddr(1) {neighbor-ip-address}";
    leaf neighbor-ip-address {
      type string;
      description
        "Neighbor IPv4 address";
    }
    leaf if-name {
      type string;
      description
        "Interface name";
    }
    leaf reason {
      type string;
      description
        "The reason the PIM neighbor connection was lost. The reasons which should interest the user:
         (1) Hold-time expired (2) Invalid state";
    }
    leaf neighbor-uptime-snmp {
      type uint32;
      description
        "The uptime when neighbor connectivity lost in TimeTicks";
    }
    leaf neighbor-uptime {
      type string;
      description
        "The uptime when neighbor connectivity lost";
    }
    leaf vrf-name {
      description
        "the vrf in which event happened";
      type string;
    }
  }

  notification PIM_INTERFACE_UP {
    description
      "The indicated PIM enabled interface is 'up'.";
    dn-events-extensions:event-severity-level "Info";
    dn-events-extensions:event-message-string "PIM enabled interface {if-name} is up. VRF instance {vrf-name}";
    dn-events-extensions:event-corrective-action-string "No corrective action.";
    dn-events-extensions:event-trigger-component-string "PIM";
    dn-events-extensions:event-group "PIM";
    dn-events-extensions:event-snmp-trap-name "dnPimInterfaceUp";
    dn-events-extensions:event-snmp-trap-oid "1.3.6.1.4.1.49739.2.5.0.2";
    dn-events-extensions:event-snmp-trap-vars "dnPimInterfaceName.0 {if-name}";
    leaf if-name {
      type string;
      description
        "Interface name";
    }
    leaf vrf-name {
      description
        "the vrf in which event happened";
      type string;
    }
  }

  notification PIM_INTERFACE_DOWN {
    description
      "The indicated PIM enabled interface is 'down'.";
    dn-events-extensions:event-severity-level "Warning";
    dn-events-extensions:event-message-string "PIM enabled interface {if-name} is down. VRF instance {vrf-name}";
    dn-events-extensions:event-corrective-action-string "No corrective action.";
    dn-events-extensions:event-trigger-component-string "PIM";
    dn-events-extensions:event-group "PIM";
    dn-events-extensions:event-snmp-trap-name "dnPimInterfaceDown";
    dn-events-extensions:event-snmp-trap-oid "1.3.6.1.4.1.49739.2.5.0.3";
    dn-events-extensions:event-snmp-trap-vars "dnPimInterfaceName.0 {if-name}";
    leaf if-name {
      type string;
      description
        "Interface name";
    }
    leaf vrf-name {
      description
        "the vrf in which event happened";
      type string;
    }
  }

  notification PIM_INVALID_REGISTER {
    description
      "An invalid PIM register message was received because the register destination does not match the rendezvous point (RP) of the group address or the group address is using an SSM (Source Specific Multicast ) address range but the PIM register message considers it to be using an ASM (Any Source Multicast) address range.";
    dn-events-extensions:event-severity-level "Warning";
    dn-events-extensions:event-message-string "Invalid PIM register message received on interface {if-name} from {origin-ip-address} for group address {group} to RP address {rp-address}. VRF instance {vrf-name}";
    dn-events-extensions:event-corrective-action-string "No corrective action.";
    dn-events-extensions:event-trigger-component-string "PIM";
    dn-events-extensions:event-group "PIM";
    dn-events-extensions:event-snmp-trap-name "pimInvalidRegister";
    dn-events-extensions:event-snmp-trap-oid "1.3.6.1.2.1.157.0.2";
    dn-events-extensions:event-snmp-trap-vars "pimGroupMappingPimMode.0 {pim-mode} ; pimInvalidRegisterAddressType.0 {address-type} ; pimInvalidRegisterOrigin.0 CONVERT inetAddr({address-type}) {origin-ip-address} ; pimInvalidRegisterGroup.0 CONVERT inetAddr({address-type}) {group} ; pimInvalidRegisterRp.0 CONVERT inetAddr({address-type}) {rp-address}";
    leaf pim-mode {
      type enumeration {
        enum none {
          value 1;
        }
        enum ssm {
          value 2;
        }
        enum asm {
          value 3;
        }
        enum bidir {
          value 4;
        }
        enum dm {
          value 5;
        }
        enum other {
          value 6;
        }
      }
      description
        "The PIM mode in which a group is operating
         SYNTAX INTEGER none(1), ssm(2), asm(3), bidir(4), dm(5), other(6)";
    }
    leaf address-type {
      type enumeration {
        enum unknown {
          value 0;
        }
        enum ipv4 {
          value 1;
        }
        enum ipv6 {
          value 2;
        }
      }
      description
        "A value that represents a type of internet address.
         SYNTAX INTEGER  unknown(0), ipv4(1), ipv6(2), ipv4z(3), ipv6z(4), dns(16)";
    }
    leaf if-name {
      type string;
      description
        "PIM register message ingress interface name";
    }
    leaf origin-ip-address {
      type string;
      description
        "The source address of the invalid register message
         received by this device";
    }
    leaf group {
      type string;
      description
        "The IP multicast group address to which the invalid
         register message received by this device was addressed";
    }
    leaf rp-address {
      type string;
      description
        "The RP address to which the invalid register message
         received by this device was delivered";
    }
    leaf vrf-name {
      description
        "the vrf in which event happened";
      type string;
    }
  }

  notification PIM_INVALID_JOIN_PRUNE {
    description
      "An invalid PIM JoinPrune message was received because the PIM register destination does not match the rendezvous point (RP) of the group address or the group address is using an SSM (Source Specific Multicast ) address range but the JoinPrune of the (*,G) or (S,G,rpt) states considers it to be using an ASM (Any Source Multicast) address range.";
    dn-events-extensions:event-severity-level "Warning";
    dn-events-extensions:event-message-string "Invalid PIM JoinPrune message received on interface {if-name} from PIM peer {origin-ip-address} for group address {group} group type {pim-mode}. RP address {rp-address}. VRF instance {vrf-name}";
    dn-events-extensions:event-corrective-action-string "No corrective action.";
    dn-events-extensions:event-trigger-component-string "PIM";
    dn-events-extensions:event-group "PIM";
    dn-events-extensions:event-snmp-trap-name "pimInvalidJoinPrune";
    dn-events-extensions:event-snmp-trap-oid "1.3.6.1.2.1.157.0.3";
    dn-events-extensions:event-snmp-trap-vars "pimGroupMappingPimMode.0 {pim-mode} ; pimInvalidJoinPruneAddressType.0 {address-type} ; pimInvalidJoinPruneOrigin.0 CONVERT inetAddr({address-type}) {origin-ip-address} ; pimInvalidJoinPruneGroup.0 CONVERT inetAddr({address-type}) {group} ; pimInvalidJoinPruneRp.0 CONVERT inetAddr({address-type}) {rp-address} ; pimNeighborUpTime {neighbor-uptime-snmp}";
    leaf pim-mode {
      type enumeration {
        enum none {
          value 1;
        }
        enum ssm {
          value 2;
        }
        enum asm {
          value 3;
        }
        enum bidir {
          value 4;
        }
        enum dm {
          value 5;
        }
        enum other {
          value 6;
        }
      }
      description
        "The PIM mode in which a group is operating
         SYNTAX INTEGER none(1), ssm(2), asm(3), bidir(4), dm(5), other(6)";
    }
    leaf address-type {
      type enumeration {
        enum unknown {
          value 0;
        }
        enum ipv4 {
          value 1;
        }
        enum ipv6 {
          value 2;
        }
      }
      description
        "A value that represents a type of internet address
         SYNTAX INTEGER  unknown(0), ipv4(1), ipv6(2), ipv4z(3), ipv6z(4), dns(16)";
    }
    leaf if-name {
      type string;
      description
        "PIM Register message ingress interface name";
    }
    leaf origin-ip-address {
      type string;
      description
        "The source address of the invalid JoinPrune message
         received by this device";
    }
    leaf group {
      type string;
      description
        "The IP multicast group address to which the invalid
         PIM JoinPrune message received by this device was addressed";
    }
    leaf rp-address {
      type string;
      description
        "The RP address to which the invalid JoinPrune message
         received by this device was delivered";
    }
    leaf neighbor-uptime-snmp {
      type uint32;
      description
        "The uptime when neighbor connectivity lost in TimeTicks";
    }
    leaf neighbor-uptime {
      type string;
      description
        "The uptime when neighbor connectivity lost";
    }
    leaf vrf-name {
      description
        "the vrf in which event happened";
      type string;
    }
  }

  notification PIM_RP_MAPPING_CHANGED {
    description
      "The active RP mapping on this device has changed.";
    dn-events-extensions:event-severity-level "Warning";
    dn-events-extensions:event-message-string "PIM RP {rp-address} mapping changed. VRF instance {vrf-name}";
    dn-events-extensions:event-corrective-action-string "No corrective action.";
    dn-events-extensions:event-trigger-component-string "PIM";
    dn-events-extensions:event-group "PIM";
    dn-events-extensions:event-snmp-trap-name "pimRPMappingChange";
    dn-events-extensions:event-snmp-trap-oid "1.3.6.1.2.1.157.0.4";
    dn-events-extensions:event-snmp-trap-vars "pimGroupMappingPimMode.0 {pim-mode} ; pimGroupMappingPrecedence.0 {group-mapping-precedence}";
    leaf pim-mode {
      type enumeration {
        enum none {
          value 1;
        }
        enum ssm {
          value 2;
        }
        enum asm {
          value 3;
        }
        enum bidir {
          value 4;
        }
        enum dm {
          value 5;
        }
        enum other {
          value 6;
        }
      }
      description
        "The PIM mode in which a group is operating
         SYNTAX INTEGER none(1), ssm(2), asm(3), bidir(4), dm(5), other(6)";
    }
    leaf rp-address {
      type string;
      description
        "The IP address of the RP for which the group mapping was changed";
    }
    leaf group-mapping-precedence {
      type uint32;
      description
        "The precedence of this row, used in the algorithm that
         determines which row applies to a given group address
         (described above).  Numerically higher values for this
         object indicate a lower precedence, with the value zero
         denoting the highest precedence.

         The absolute values of this object have a significance only
         on the local router and do not need to be coordinated with
         other routers.";
    }
    leaf vrf-name {
      description
        "the vrf in which event happened";
      type string;
    }
  }

  notification PIM_INTERNAL_ERROR {
    description
      "A PIM has failed due to an internal error.";
    dn-events-extensions:event-severity-level "Error";
    dn-events-extensions:event-message-string "PIM internal error: {error-type}, {error-message}. VRF instance {vrf-name}";
    dn-events-extensions:event-corrective-action-string "Copy the error message and contact Customer Support.";
    dn-events-extensions:event-trigger-component-string "PIM";
    dn-events-extensions:event-group "PIM";
    leaf error-type {
      type string;
      description
        "The PIM internal error type";
    }
    leaf error-message {
      type string;
      description
        "The PIM error message";
    }
    leaf vrf-name {
      description
        "the vrf in which event happened";
      type string;
    }
  }

  notification PIM_MAXIMUM_MFIB_ROUTES_LIMIT_REACHED {
    description
      "The maximum number of concurrent MFIB routes installed by PIM has reached the configured system limit.";
    dn-events-extensions:event-severity-level "Warning";
    dn-events-extensions:event-message-string "The system limit of {limit} MFIB routes installed by PIM has been reached. VRF instance {vrf-name}";
    dn-events-extensions:event-corrective-action-string "Review the PIM configuration in the network.";
    dn-events-extensions:event-trigger-component-string "PIM";
    dn-events-extensions:event-group "PIM";
    leaf limit {
      type uint32;
      description
        "The PIM MFIB routes maximum limit";
    }
    leaf vrf-name {
      type string;
      description
        "VRF name";
      default "all";
    }
  }

  notification PIM_MAXIMUM_MFIB_ROUTES_LIMIT_CLEARED {
    description
      "The number of concurrent MFIB routes installed by PIM has dropped below the configured maximum limit.";
    dn-events-extensions:event-severity-level "Info";
    dn-events-extensions:event-message-string "The number of MFIB routes installed by PIM has dropped below the system limit of {limit}. VRF instance {vrf-name}";
    dn-events-extensions:event-corrective-action-string "This is informational, no corrective action required.";
    dn-events-extensions:event-trigger-component-string "PIM";
    dn-events-extensions:event-group "PIM";
    leaf limit {
      type uint32;
      description
        "The PIM MFIB routes maximum limit";
    }
    leaf vrf-name {
      type string;
      description
        "VRF name";
      default "all";
    }
  }

  notification PIM_MAXIMUM_MFIB_ROUTES_THRESHOLD_EXCEEDED {
    description
      "The number of concurrent MFIB routes installed by PIM has crossed the system threshold.";
    dn-events-extensions:event-severity-level "Notice";
    dn-events-extensions:event-message-string "The number of MFIB routes installed by PIM has crossed the system threshold {threshold}% of the system limit of {limit}, the current number of MFIB routes is {actual-pim-mfib-entries}. VRF instance {vrf-name}";
    dn-events-extensions:event-corrective-action-string "No corrective action.";
    dn-events-extensions:event-trigger-component-string "PIM";
    dn-events-extensions:event-group "PIM";
    leaf threshold {
      type uint8;
      description
        "Threshold percent";
    }
    leaf limit {
      type uint32;
      description
        "The PIM MFIB routes maximum limit";
    }
    leaf actual-pim-mfib-entries {
      type uint32;
      description
        "The current number of PIM MFIB routes";
    }
    leaf vrf-name {
      type string;
      description
        "VRF name";
      default "all";
    }
  }

  notification PIM_MAXIMUM_MFIB_ROUTES_THRESHOLD_CLEARED {
    description
      "The number of concurrent MFIB routes installed by PIM has dropped below the configured system threshold.";
    dn-events-extensions:event-severity-level "Info";
    dn-events-extensions:event-message-string "The number of MFIB routes installd by PIM has dropped below the system threshold {threshold}% of the system limit of {limit}, the current number of MFIB routes is {actual-pim-mfib-entries}. VRF instance {vrf-name}";
    dn-events-extensions:event-corrective-action-string "This is informational, no corrective action required.";
    dn-events-extensions:event-trigger-component-string "PIM";
    dn-events-extensions:event-group "PIM";
    leaf threshold {
      type uint8;
      description
        "Threshold percent";
    }
    leaf limit {
      type uint32;
      description
        "The PIM MFIB routes maximum limit";
    }
    leaf actual-pim-mfib-entries {
      type uint32;
      description
        "The current number of PIM MFIB routes";
    }
    leaf vrf-name {
      type string;
      description
        "VRF name";
      default "all";
    }
  }

  notification PIM_NSR_CONFIG {
    description
      "The PIM NSR (Non-Stop Routing) admin-state configuration was changed by the user listed.";
    dn-events-extensions:event-severity-level "Info";
    dn-events-extensions:event-message-string "User {user-name} has changed PIM NSR admin-state configuration to {new-state}";
    dn-events-extensions:event-corrective-action-string "This is informational, no corrective action required.";
    dn-events-extensions:event-trigger-component-string "PIM";
    dn-events-extensions:event-group "PIM";
    leaf user-name {
      type string;
      description
        "Username";
    }
    leaf new-state {
      type enumeration {
        enum enabled;
        enum disabled;
      }
      description
        "PIM NSR admin-state";
    }
  }

  notification PIM_NSR_RECOVERY_START {
    description
      "The system has started PIM Non-Stop Routing recovery due to a restart of the pimd process.";
    dn-events-extensions:event-severity-level "Info";
    dn-events-extensions:event-message-string "pimd process is starting a Non-Stop Routing recovery attempt due to process restart";
    dn-events-extensions:event-corrective-action-string "This is informational, no corrective action required.";
    dn-events-extensions:event-trigger-component-string "PIM";
    dn-events-extensions:event-group "PIM";
  }

  notification PIM_NSR_RECOVERED {
    description
      "The system performed a PIM Non-Stop Routing recovery due to a restart of the pimd process.";
    dn-events-extensions:event-severity-level "Notice";
    dn-events-extensions:event-message-string "PIM Non-Stop Routing recovery was performed successfully due to a restart of the pimd process";
    dn-events-extensions:event-corrective-action-string "This is informational, no corrective action required.";
    dn-events-extensions:event-trigger-component-string "PIM";
    dn-events-extensions:event-group "PIM";
  }

  notification PIM_NSR_RECOVERY_FAILED {
    description
      "The PIM process failed to recover in Non-Stop Routing mode.";
    dn-events-extensions:event-severity-level "Warning";
    dn-events-extensions:event-message-string "pimd process failed to recover in Non-Stop Routing mode";
    dn-events-extensions:event-corrective-action-string "Verify NSR readiness prior to the failure event. If the database was synchronized prior to the failure event, contact Customer Support.";
    dn-events-extensions:event-trigger-component-string "PIM";
    dn-events-extensions:event-group "PIM";
  }

  notification PIM_GRACEFUL_RESTART_STATUS_CHANGE {
    description
      "The PIM Graceful Restart status has changed.";
    dn-events-extensions:event-severity-level "Info";
    dn-events-extensions:event-message-string "PIM Graceful Restart {status}. Grace period {grace-period} seconds";
    dn-events-extensions:event-corrective-action-string "This is informational, no corrective action required.";
    dn-events-extensions:event-trigger-component-string "PIM";
    dn-events-extensions:event-group "PIM";
    leaf status {
      type enumeration {
        enum started {
          value 1;
          description
            "Graceful restart has been initiated";
        }
        enum completed {
          value 2;
          description
            "Graceful restart completed successfully";
        }
        enum failed {
          value 3;
          description
            "Graceful restart failed or timed out";
        }
      }
      description
        "Current status of PIM graceful restart operation.";
    }
    leaf grace-period {
      type uint16 {
        range "30..3600";
      }
      description
        "Configured PIM graceful restart timeout interval.";
    }
  }

  notification MULTICAST_ONLY_FRR_SWITCHOVER {
    description
      "MoFRR switchover event took place.";
    dn-events-extensions:event-severity-level "Info";
    dn-events-extensions:event-message-string "An MoFRR protected (S,G) entry with source IP address {source-ip-address} and group address {group-ip-address} switched over to incoming interface {in-interface-name} in VRF {vrf-name}.";
    dn-events-extensions:event-corrective-action-string "This is informational, no corrective action required.";
    dn-events-extensions:event-trigger-component-string "PIM";
    dn-events-extensions:event-group "Multicast";
    leaf source-ip-address {
      type string;
      description
        "Neighbor IP address";
    }
    leaf group-ip-address {
      type string;
      description
        "Group IP address";
    }
    leaf in-interface-name {
      type string;
      description
        "New incoming interface name";
    }
    leaf vrf-name {
      type string;
      description
        "Vrf name";
    }
  }

  // MSDP Events

  notification MSDP_PEER_UP {
    description
      "The MSDP peer connectivity is 'up'. This can occur when the peer connectivity is first established or when connectivity is restored.";
    dn-events-extensions:event-severity-level "Info";
    dn-events-extensions:event-message-string "MSDP peer connectivity with peer {peer-ip-address} is up";
    dn-events-extensions:event-corrective-action-string "This is informational, no corrective action required.";
    dn-events-extensions:event-trigger-component-string "MSDP";
    dn-events-extensions:event-group "MSDP";
    leaf peer-ip-address {
      type string;
      description
        "MSDP peer IP address";
    }
  }

  notification MSDP_PEER_DOWN {
    description
      "The MSDP peer connectivity has been lost with the indicated peer.";
    dn-events-extensions:event-severity-level "Warning";
    dn-events-extensions:event-message-string "MSDP peer connectivity lost with peer {peer-ip-address}. Connectivity loss reason: {reason}. Uptime: {uptime}";
    dn-events-extensions:event-corrective-action-string "No corrective action.";
    dn-events-extensions:event-trigger-component-string "MSDP";
    dn-events-extensions:event-group "MSDP";
    leaf peer-ip-address {
      type string;
      description
        "MSDP peer IPv4 address";
    }
    leaf reason {
      type string;
      description
        "The reason of losing the MSDP peer connection. The interesting reasons for the user are:
         (1) Hold-timer expired. (2) Session cleared by user (3) TCP session reset by peer";
    }
    leaf uptime {
      type string;
      description
        "The connectivity uptime when MSDP peer connectivity lost";
    }
  }

  notification MSDP_INTERNAL_ERROR {
    description
      "MSDP has encountered an internal error.";
    dn-events-extensions:event-severity-level "Error";
    dn-events-extensions:event-message-string "MSDP has encountered an error: {error-type}, {error-message}";
    dn-events-extensions:event-corrective-action-string "No corrective action.";
    dn-events-extensions:event-trigger-component-string "MSDP";
    dn-events-extensions:event-group "MSDP";
    leaf error-type {
      type string;
      description
        "The MSDP internal error type";
    }
    leaf error-message {
      type string;
      description
        "The MSDP internal error message";
    }
  }

  notification MSDP_MAXIMUM_SA_STATES_LIMIT_REACHED {
    description
      "The number of MSDP SA states has reached the configured system limit.";
    dn-events-extensions:event-severity-level "Warning";
    dn-events-extensions:event-message-string "Number of MSDP SA states has reached system limit of {limit}";
    dn-events-extensions:event-corrective-action-string "Review the MSDP configuration in the network.";
    dn-events-extensions:event-trigger-component-string "MSDP";
    dn-events-extensions:event-group "MSDP";
    leaf limit {
      type uint32;
      description
        "The MSDP SA states limit number";
    }
  }

  notification MSDP_MAXIMUM_SA_STATES_LIMIT_CLEARED {
    description
      "MSDP SA states number have moved below the system limit.";
    dn-events-extensions:event-severity-level "Info";
    dn-events-extensions:event-message-string "Number of MSDP SA states is below the system limit of {limit}";
    dn-events-extensions:event-corrective-action-string "This is informational, no corrective action required.";
    dn-events-extensions:event-trigger-component-string "MSDP";
    dn-events-extensions:event-group "MSDP";
    leaf limit {
      type uint32;
      description
        "The MSDP SA states limit";
    }
  }

  notification MSDP_MAXIMUM_SA_STATES_THRESHOLD_EXCEEDED {
    description
      "The number of MSDP SA states has crossed the system threshold.";
    dn-events-extensions:event-severity-level "Notice";
    dn-events-extensions:event-message-string "Number of MSDP SA states has crossed the system threshold {threshold}% limit {limit}, the number of MSDP SA states ({actual-msdp-sa-states})";
    dn-events-extensions:event-corrective-action-string "Review the MSDP configuration in the network.";
    dn-events-extensions:event-trigger-component-string "MSDP";
    dn-events-extensions:event-group "MSDP";
    leaf threshold {
      type uint8;
      description
        "Threshold percent";
    }
    leaf limit {
      type uint32;
      description
        "The MSDP SA states maximum limit";
    }
    leaf actual-msdp-sa-states {
      type uint32;
      description
        "The current MSDP SA states";
    }
  }

  notification MSDP_MAXIMUM_SA_STATES_THRESHOLD_CLEARED {
    description
      "The number of MSDP SA states have moved below the system threshold.";
    dn-events-extensions:event-severity-level "Info";
    dn-events-extensions:event-message-string "Number of MSDP SA states is below the system threshold {threshold}% of the limit ({limit}), the current number of MSDP SA states is ({actual-msdp-sa-states})";
    dn-events-extensions:event-corrective-action-string "This is informational, no corrective action required.";
    dn-events-extensions:event-trigger-component-string "MSDP";
    dn-events-extensions:event-group "MSDP";
    leaf threshold {
      type uint8;
      description
        "Threshold percent";
    }
    leaf limit {
      type uint32;
      description
        "The MSDP SA states threshold";
    }
    leaf actual-msdp-sa-states {
      type uint32;
      description
        "The current MSDP SA states";
    }
  }

  notification MSDP_SA_LOOP_DETECTED {
    description
      "MSDP SA loop was detected.";
    dn-events-extensions:event-severity-level "Warning";
    dn-events-extensions:event-message-string "MSDP SA loop detected. Originator RP with local address {originator-ip-address} received self originated SA message from peer {peer-ip-address}.";
    dn-events-extensions:event-corrective-action-string "Check the network topology/configuration.";
    dn-events-extensions:event-trigger-component-string "MSDP";
    dn-events-extensions:event-group "MSDP";
    leaf originator-ip-address {
      type string;
      description
        "Originator RP local IP address";
    }
    leaf peer-ip-address {
      type string;
      description
        "MSDP peer IP address";
    }
  }

  notification MSDP_SA_LOOP_CLEARED {
    description
      "MSDP SA loop was cleared.";
    dn-events-extensions:event-severity-level "Info";
    dn-events-extensions:event-message-string "MSDP SA loop detected between Originator RP with local address {originator-ip-address} and peer {peer-ip-address} was cleared.";
    dn-events-extensions:event-corrective-action-string "This is informational, no corrective action required.";
    dn-events-extensions:event-trigger-component-string "MSDP";
    dn-events-extensions:event-group "MSDP";
    leaf originator-ip-address {
      type string;
      description
        "Originator RP local IP address";
    }
    leaf peer-ip-address {
      type string;
      description
        "MSDP peer IP address";
    }
  }

  // MPLS Events

  notification MPLS_MAXIMUM_LABELS_ALLOCATION_LIMIT_REACHED {
    description
      "The MPLS maximum label allocation for the listed routing protocol has reached the limit.";
    dn-events-extensions:event-severity-level "Warning";
    dn-events-extensions:event-message-string "MPLS maximum label allocation for protocol {protocol} reached the system limit of {limit}";
    dn-events-extensions:event-corrective-action-string "Clear inactive LSPs.";
    dn-events-extensions:event-trigger-component-string "RIB-manager";
    dn-events-extensions:event-group "MPLS";
    leaf protocol {
      type string;
      description
        "MPLS control protocol name";
    }
    leaf limit {
      type uint32;
      description
        "The label space scale, default 20bit space (1048576)";
    }
  }

  notification MPLS_MAXIMUM_LABELS_ALLOCATION_LIMIT_CLEARED {
    description
      "The MPLS maximum label allocation for the listed routing protocol has moved below the system limit.";
    dn-events-extensions:event-severity-level "Warning";
    dn-events-extensions:event-message-string "MPLS maximum label allocation for protocol {protocol} is below the system limit {limit}";
    dn-events-extensions:event-corrective-action-string "No corrective action.";
    dn-events-extensions:event-trigger-component-string "RIB-manager";
    dn-events-extensions:event-group "MPLS";
    leaf protocol {
      type string;
      description
        "MPLS control protocol name";
    }
    leaf limit {
      type uint32;
      description
        "The label space scale, default 20bit space (1048576)";
    }
  }

  notification MPLS_MAXIMUM_LABELS_ALLOCATION_THRESHOLD_EXCEEDED {
    description
      "MPLS maximum label allocation for the listed routing protocol has crossed the system threshold.";
    dn-events-extensions:event-severity-level "Notice";
    dn-events-extensions:event-message-string "MPLS maximum label allocation for protocol {protocol} crossed the system threshold {threshold}% of the limit ({limit}), the current number of MLPS labels are ({numeric-value})";
    dn-events-extensions:event-corrective-action-string "Clear inactive LSPs.";
    dn-events-extensions:event-trigger-component-string "RIB-manager";
    dn-events-extensions:event-group "MPLS";
    leaf protocol {
      type string;
      description
        "MPLS control protocol name";
    }
    leaf numeric-value {
      type uint16;
      description
        "Current number of MPLS labels allocated for the specified protocol";
    }
    leaf limit {
      description
        "Maximum label allocation limit for the specified protocol";
      type uint32;
    }
    leaf threshold {
      type uint8;
      description
        "Threshold percent";
    }
  }

  notification MPLS_MAXIMUM_LABELS_ALLOCATION_THRESHOLD_CLEARED {
    description
      "The MPLS maximum label allocation for the listed routing protocol has moved below the threshold.";
    dn-events-extensions:event-severity-level "Info";
    dn-events-extensions:event-message-string "MPLS Maximum label allocation for protocol {protocol} is below the threshold {threshold}% of the limit ({limit}), the current number of MPLS labels are ({numeric-value})";
    dn-events-extensions:event-corrective-action-string "This is informational, no corrective action required.";
    dn-events-extensions:event-trigger-component-string "RIB-manager";
    dn-events-extensions:event-group "MPLS";
    leaf protocol {
      type string;
      description
        "MPLS control protocol name";
    }
    leaf numeric-value {
      type uint32;
      description
        "Current number of MPLS labels allocated for the specified protocol";
    }
    leaf limit {
      description
        "Maximum label allocation limit for the specified protocol";
      type uint32;
    }
    leaf threshold {
      type uint8;
      description
        "Threshold percent";
    }
  }

  notification MPLS_MAXIMUM_LABEL_COUNTERS_RESOURCE_LIMIT_REACHED {
    description
      "The number of allocated MPLS label counters has reached the resource limit.";
    dn-events-extensions:event-severity-level "Warning";
    dn-events-extensions:event-message-string "Number of allocated MPLS label counters has reached the resource limit of {label-counters-resource-limit} counters";
    dn-events-extensions:event-corrective-action-string "Limit the number of LDP or SR routes.";
    dn-events-extensions:event-trigger-component-string "WB Agent";
    dn-events-extensions:event-group "MPLS";
    leaf label-counters-resource-limit {
      description
        "Maximum label counters resource limit";
      type uint32;
    }
  }

  notification MPLS_MAXIMUM_LABEL_COUNTERS_RESOURCE_LIMIT_CLEARED {
    description
      "The number of allocated MPLS label counters has moved below the resource limit.";
    dn-events-extensions:event-severity-level "Info";
    dn-events-extensions:event-message-string "Number of allocated MPLS label counters is below the limit of {label-counters-resource-limit} counters";
    dn-events-extensions:event-corrective-action-string "This is informational, no corrective action required.";
    dn-events-extensions:event-trigger-component-string "WB Agent";
    dn-events-extensions:event-group "MPLS";
    leaf label-counters-resource-limit {
      description
        "Maximum label counters resource limit";
      type uint32;
    }
  }

  // Static Route events

  notification STATIC_ROUTE_MAXIMUM_ROUTES_LIMIT_REACHED {
    description
      "The number of static routes has reached the system limit, no additional static routes can be added.";
    dn-events-extensions:event-severity-level "Warning";
    dn-events-extensions:event-message-string "Number of static routes in VRF {vrf-name} has reached the system limit of {limit}";
    dn-events-extensions:event-corrective-action-string "Remove unrequired static routes.";
    dn-events-extensions:event-trigger-component-string "Static-route";
    dn-events-extensions:event-group "Static-route";
    leaf vrf-name {
      description
        "the vrf in which event happened";
      type string;
    }
    leaf limit {
      type uint16;
      description
        "Maximum number of sessions";
    }
  }

  notification STATIC_ROUTE_MAXIMUM_ROUTES_LIMIT_CLEARED {
    description
      "Static routes have been removed, the number of static routes have moved below the system limit allowing additional routes to be added.";
    dn-events-extensions:event-severity-level "Info";
    dn-events-extensions:event-message-string "Number of static routes in VRF {vrf-name} is below the system limit of {limit}";
    dn-events-extensions:event-corrective-action-string "This is informational, no corrective action required.";
    dn-events-extensions:event-trigger-component-string "Static-route";
    dn-events-extensions:event-group "Static-route";
    leaf vrf-name {
      description
        "the vrf in which event happened";
      type string;
    }
    leaf limit {
      type uint16;
      description
        "Maximum number of sessions";
    }
  }

  notification STATIC_ROUTE_MAXIMUM_ROUTES_THRESHOLD_EXCEEDED {
    description
      "The number of static routes has crossed the system threshold.";
    dn-events-extensions:event-severity-level "Notice";
    dn-events-extensions:event-message-string "Number of static routes in VRF {vrf-name} has crossed the system threshold {threshold}% of the limit ({limit}), the current number of static routes are ({numeric-value})";
    dn-events-extensions:event-corrective-action-string "Remove unrequired static routes.";
    dn-events-extensions:event-trigger-component-string "Static-route";
    dn-events-extensions:event-group "Static-route";
    leaf vrf-name {
      description
        "the vrf in which event happened";
      type string;
    }
    leaf threshold {
      type uint8;
      description
        "Limit percent threshold";
    }
    leaf numeric-value {
      type uint16;
      description
        "Current number of bfd sessions";
    }
    leaf limit {
      type uint16;
      description
        "Maximum number of sessions";
    }
  }

  notification STATIC_ROUTE_MAXIMUM_ROUTES_THRESHOLD_CLEARED {
    description
      "The number of static routes is below the system threshold.";
    dn-events-extensions:event-severity-level "Info";
    dn-events-extensions:event-message-string "Number of static routes in VRF {vrf-name} is below the system threshold {threshold}% of the limit ({limit}), the current number of static routes are ({numeric-value})";
    dn-events-extensions:event-corrective-action-string "This is informational, no corrective action required.";
    dn-events-extensions:event-trigger-component-string "Static-route";
    dn-events-extensions:event-group "Static-route";
    leaf vrf-name {
      description
        "the vrf in which event happened";
      type string;
    }
    leaf threshold {
      type uint8;
      description
        "Limit percent threshold";
    }
    leaf numeric-value {
      type uint16;
      description
        "Current number of BFD sessions";
    }
    leaf limit {
      type uint16;
      description
        "Maximum number of sessions";
    }
  }

  // TCP events

  notification TCP_AUTHENTICATION_FAILED {
    description
      "Failed to authenticate the TCP session.";
    dn-events-extensions:event-severity-level "Notice";
    dn-events-extensions:event-message-string "Failed to authenticate the TCP session from the local address {local-address-port} to the remote address {remote-address-port}";
    dn-events-extensions:event-corrective-action-string "Verify that the session peer is configured with the correct password.";
    dn-events-extensions:event-trigger-component-string "OS";
    dn-events-extensions:event-group "TCP";
    leaf local-address-port {
      type string;
      description
        "The local IPv4/6 address with port number in format of address::port";
    }
    leaf remote-address-port {
      type string;
      description
        "The remote IPv4/6 address with port number in format of address::port";
    }
  }

  notification TCP_AUTHENTICATION_TYPE_FAILED {
    description
      "TCP authentication settings mismatch between peers.";
    dn-events-extensions:event-severity-level "Notice";
    dn-events-extensions:event-message-string "TCP authentication settings mismatch between peers for TCP session from the local address {local-address-port} to the remote address {remote-address-port}. Authentication required on {side} system";
    dn-events-extensions:event-corrective-action-string "Verify that the session peer authentication configuration is the same as the local configuration.";
    dn-events-extensions:event-trigger-component-string "OS";
    dn-events-extensions:event-group "TCP";
    leaf local-address-port {
      type string;
      description
        "The local IPv4/6 address with port number in format of address::port";
    }
    leaf remote-address-port {
      type string;
      description
        "The remote IPv4/6 address with port number in format of address::port";
    }
    leaf side {
      description
        "The system on which authentication is required, local or remote";
      type string;
    }
  }

  notification TCP_MAXIMUM_CONNECTION_ATTEMPTS_REACHED {
    description
      "A new control connection attempt, for example, by an SSH session, was ignored because the number of control protocols connection attempts has reached the configured limit.";
    dn-events-extensions:event-severity-level "Warning";
    dn-events-extensions:event-message-string "A new {service-type} connection on port {local-address-port} from remote address {remote-address-port} has been ignored since the number of control connection attempts within a time window of {time-window} has reached the configured limit of {max-attempts}";
    dn-events-extensions:event-corrective-action-string "Check control protocols such as SSH and Netconf connection attempt rate.";
    dn-events-extensions:event-trigger-component-string "OS";
    dn-events-extensions:event-group "TCP";
    leaf service-type {
      type enumeration {
        enum ssh;
        enum netconf;
      }
      description
        "Control connection service type";
    }
    leaf local-address-port {
      type string;
      description
        "The local IPv4/6 address with port number in format of address::port";
    }
    leaf remote-address-port {
      type string;
      description
        "The remote IPv4/6 address with port number in format of address::port";
    }
    leaf time-window {
      type uint16;
      description
        "Length in seconds of connection attempts time window";
    }
    leaf max-attempts {
      type uint8;
      description
        "Maximum number of connection attempts";
    }
  }

  notification TCP_MAXIMUM_CONNECTION_ATTEMPTS_CLEARED {
    description
      "A new control connection attempt, for example, by an SSH session, was accepted after rate limit conditions have been cleared.";
    dn-events-extensions:event-severity-level "Notice";
    dn-events-extensions:event-message-string "A new {service-type} connection on port {local-address-port} from remote address {remote-address-port} was accepted since the number of control connection attempts within a time window of {time-window} is below or equal to the configured limit of {max-attempts}";
    dn-events-extensions:event-corrective-action-string "Check control protocols such as SSH and Netconf connection attempt rate.";
    dn-events-extensions:event-trigger-component-string "OS";
    dn-events-extensions:event-group "TCP";
    leaf service-type {
      type enumeration {
        enum ssh;
        enum netconf;
      }
      description
        "Control connection service type";
    }
    leaf local-address-port {
      type string;
      description
        "The local IPv4/6 address with port number in format of address::port";
    }
    leaf remote-address-port {
      type string;
      description
        "The remote IPv4/6 address with port number in format of address::port";
    }
    leaf time-window {
      type uint16;
      description
        "Length in seconds of connection attempts time window";
    }
    leaf max-attempts {
      type uint8;
      description
        "Maximum number of connection attempts";
    }
  }

  notification MPLS_OAM_PROBE_LOSS_THRESHOLD_REACHED {
    description
      "MPLS OAM probe loss has reached the configured threshold.";
    dn-events-extensions:event-severity-level "Warning";
    dn-events-extensions:event-message-string "MPLS OAM service {profile-name} for tunnel {tunnel-name} has reached the configured threshold of {threshold}";
    dn-events-extensions:event-corrective-action-string "Verify the tunnel state and try to optimize the tunnel.";
    dn-events-extensions:event-trigger-component-string "RSVP";
    dn-events-extensions:event-group "MPLS-OAM";
    leaf profile-name {
      type string;
      description
        "Mpls oam profile name";
    }
    leaf tunnel-name {
      type string;
      description
        "Tunnel name";
    }
    leaf threshold {
      type uint8;
      description
        "Probe loss threshold";
    }
  }

  notification MPLS_OAM_PROBE_LOSS_THRESHOLD_CLEARED {
    description
      "MPLS Operation, Administration, and Maintenance (OAM) probe loss is below the configured threshold.";
    dn-events-extensions:event-severity-level "Info";
    dn-events-extensions:event-message-string "MPLS OAM service {profile-name} for tunnel {tunnel-name} is below the configured threshold of {threshold}";
    dn-events-extensions:event-corrective-action-string "This is informational, no corrective action required.";
    dn-events-extensions:event-trigger-component-string "RSVP";
    dn-events-extensions:event-group "MPLS-OAM";
    leaf profile-name {
      type string;
      description
        "MPLS OAM profile name";
    }
    leaf tunnel-name {
      type string;
      description
        "Tunnel name";
    }
    leaf threshold {
      type uint8;
      description
        "Probe loss threshold";
    }
  }

  notification L2VPN_MPLS_OAM_PROBE_LOSS_THRESHOLD_REACHED {
    description
      "L2VPN MPLS OAM probe loss has reached the configured threshold.";
    dn-events-extensions:event-severity-level "Warning";
    dn-events-extensions:event-message-string "MPLS OAM service {profile-name} for service {service-name} against target-addrss {target-address} has reached the configured threshold of {threshold}";
    dn-events-extensions:event-corrective-action-string "Verify the service state and try to optimize the service.";
    dn-events-extensions:event-trigger-component-string "L2VPN";
    dn-events-extensions:event-group "MPLS-OAM";
    leaf profile-name {
      type string;
      description
        "Mpls oam profile name";
    }
    leaf service-name {
      type string;
      description
        "L2VPN service name";
    }
    leaf target-address {
      type string;
      description
        "PW peer IP address";
    }
    leaf threshold {
      type uint8;
      description
        "Probe loss threshold";
    }
  }

  notification L2VPN_MPLS_OAM_PROBE_LOSS_THRESHOLD_CLEARED {
    description
      "MPLS Operation, Administration, and Maintenance (OAM) probe loss is below the configured threshold.";
    dn-events-extensions:event-severity-level "Info";
    dn-events-extensions:event-message-string "MPLS OAM service {profile-name} for service {service-name} against target-addrss {target-address} is below the configured threshold of {threshold}";
    dn-events-extensions:event-corrective-action-string "This is informational, no corrective action required.";
    dn-events-extensions:event-trigger-component-string "L2VPN";
    dn-events-extensions:event-group "MPLS-OAM";
    leaf profile-name {
      type string;
      description
        "MPLS OAM profile name";
    }
    leaf service-name {
      type string;
      description
        "Tunnel name";
    }
    leaf target-address {
      type string;
      description
        "PW peer IP address";
    }
    leaf threshold {
      type uint8;
      description
        "Probe loss threshold";
    }
  }

  // 802.3ah EFM OAM events

  notification EFM_OAM_SESSION_UP {
    description
      "The EFM OAM session on the specified interface has moved from a 'down' state to a 'up' state.";
    dn-events-extensions:event-severity-level "Info";
    dn-events-extensions:event-message-string "EFM OAM session on interface {if-name} with neighbor {neighbor-address} has been established.";
    dn-events-extensions:event-corrective-action-string "This is informational, no corrective action required.";
    dn-events-extensions:event-trigger-component-string "WB Agent";
    dn-events-extensions:event-group "EFM-OAM";
    leaf if-name {
      type string;
      description
        "Local interface name";
    }
    leaf neighbor-address {
      type string;
      description
        "Neighbor peer MAC address";
    }
  }

  notification EFM_OAM_SESSION_DOWN {
    description
      "The EFM OAM session on the specified interface has moved from an 'up' state to a 'down' state.";
    dn-events-extensions:event-severity-level "Info";
    dn-events-extensions:event-message-string "EFM OAM session on interface {if-name} with neighbor {neighbor-address} has been terminated.";
    dn-events-extensions:event-corrective-action-string "Verify link connectivity, its status and that the protocol is enabled on both sides.";
    dn-events-extensions:event-trigger-component-string "WB Agent";
    dn-events-extensions:event-group "EFM-OAM";
    leaf if-name {
      type string;
      description
        "Local interface name";
    }
    leaf neighbor-address {
      type string;
      description
        "Neighbor peer MAC address";
    }
  }

  notification EFM_OAM_LINK_EVENT_THRESHOLD_EXCEEDED {
    description
      "An EFM OAM link event has occured on the specified interface, a link performance threshold has been exceeded.";
    dn-events-extensions:event-severity-level "Warning";
    dn-events-extensions:event-message-string "The {location} EFM-OAM {link-event} threshold on interface {if-name} connected to {neighbor-address} has been exceeded. Reported link event details: window-size {window-size}; threshold {link-event-threshold}; errors value within window {errors-value}; total errors {total-errors}; total events sent {total-events}.";
    dn-events-extensions:event-corrective-action-string "Check the optical equipment and cabling.";
    dn-events-extensions:event-trigger-component-string "WB Agent";
    dn-events-extensions:event-group "EFM-OAM";
    leaf location {
      type enumeration {
        enum local;
        enum remote;
      }
      description
        "Link event origin";
    }
    leaf link-event {
      type enumeration {
        enum errored-symbol-period-event;
        enum errored-frame-event;
        enum errored-frame-period-event;
        enum errored-frame-seconds-summary-event;
      }
      description
        "Measured link performance KPI";
    }
    leaf if-name {
      type string;
      description
        "Local interface name";
    }
    leaf neighbor-address {
      type string;
      description
        "Neighbor peer MAC addres";
    }
    leaf window-size {
      type uint64;
      description
        "The sampling window for the reported link event";
    }
    leaf link-event-threshold {
      type uint16;
      description
        "The configured threshold value for the reported link event";
    }
    leaf errors-value {
      type uint16;
      description
        "The number of errors reported for the link event within the sampling window";
    }
    leaf total-errors {
      type uint64;
      description
        "The total number of errors causing the link event to be sent";
    }
    leaf total-events {
      type uint32;
      description
        "The total number of times that the reported link event was sent";
    }
  }

  notification EFM_OAM_LINK_EVENT_THRESHOLD_CLEARED {
    description
      "An EFM OAM link event on the specified interface has ended, a link performance threshold violation has been cleared.";
    dn-events-extensions:event-severity-level "Info";
    dn-events-extensions:event-message-string "The {location} EFM-OAM {link-event} threshold violation on interface {if-name} connected to {neighbor-address} has been cleared.";
    dn-events-extensions:event-corrective-action-string "This is informational, no corrective action required.";
    dn-events-extensions:event-trigger-component-string "WB Agent";
    dn-events-extensions:event-group "EFM-OAM";
    leaf location {
      type enumeration {
        enum local;
        enum remote;
      }
      description
        "Link event origin";
    }
    leaf link-event {
      type enumeration {
        enum errored-symbol-period-event;
        enum errored-frame-event;
        enum errored-frame-period-event;
        enum errored-frame-seconds-summary-event;
      }
      description
        "Measured link performance KPI";
    }
    leaf if-name {
      type string;
      description
        "Local interface name";
    }
    leaf neighbor-address {
      type string;
      description
        "Neighbor peer MAC addres";
    }
  }

  notification EFM_OAM_CRITICAL_LINK_EVENT_TRIGGERED {
    description
      "An EFM OAM critical link event on the specified interface has been triggered.";
    dn-events-extensions:event-severity-level "Critical";
    dn-events-extensions:event-message-string "A {location} EFM-OAM {critical-link-event} event has been generated on interface {if-name} with neighbor {neighbor-address}. {action} shall be performed.";
    dn-events-extensions:event-corrective-action-string "Check the optical equipment and cabling.";
    dn-events-extensions:event-trigger-component-string "WB Agent";
    dn-events-extensions:event-group "EFM-OAM";
    leaf location {
      type enumeration {
        enum local;
        enum remote;
      }
      description
        "Critical link event origin";
    }
    leaf critical-link-event {
      type enumeration {
        enum link-fault;
        enum dying-gasp;
        enum critical-link;
      }
      description
        "Reported critical link event";
    }
    leaf if-name {
      type string;
      description
        "Local interface name";
    }
    leaf neighbor-address {
      type string;
      description
        "Neighbor peer MAC address";
    }
    leaf action {
      type enumeration {
        enum no-action;
        enum disable-interface;
      }
      description
        "Action to be performed following the critical link event reported";
    }
  }

  notification EFM_OAM_CRITICAL_LINK_EVENT_CLEARED {
    description
      "An EFM OAM critical link event on the specified interface has been cleared.";
    dn-events-extensions:event-severity-level "Info";
    dn-events-extensions:event-message-string "A {location} EFM-OAM {critical-link-event} event on interface {if-name} with neighbor {neighbor-address} has been cleared.";
    dn-events-extensions:event-corrective-action-string "This is informational, no corrective action required.";
    dn-events-extensions:event-trigger-component-string "WB Agent";
    dn-events-extensions:event-group "EFM-OAM";
    leaf location {
      type enumeration {
        enum local;
        enum remote;
      }
      description
        "Critical link event origin";
    }
    leaf critical-link-event {
      type enumeration {
        enum link-fault;
        enum dying-gasp;
        enum critical-link-event;
      }
      description
        "Reported critical link event";
    }
    leaf if-name {
      type string;
      description
        "Local interface name";
    }
    leaf neighbor-address {
      type string;
      description
        "Neighbor peer MAC addres";
    }
  }

  // 802.1ag CFM OAM events

  notification CFM_DEFECT_CONDITION_DETECTED {
    description
      "A defect condition was detected in a CFM service.";
    dn-events-extensions:event-severity-level "Warning";
    dn-events-extensions:event-message-string "A {highest-defect} CFM defect was detected in level {md-level} maintenance-domain {maintenance-domain-name} (MD-name {md-name}), maintenance-association {maintenance-association-name} (short-MA-name {short-ma-name}). {action} shall be performed.";
    dn-events-extensions:event-corrective-action-string "Review CFM configuration in the network and cabling.";
    dn-events-extensions:event-trigger-component-string "WB Agent";
    dn-events-extensions:event-group "CFM-OAM";
    dn-events-extensions:event-snmp-trap-name "dnCfmFaultAlarm";
    dn-events-extensions:event-snmp-trap-oid "1.3.6.1.4.1.49739.2.15.0.1";
    dn-events-extensions:event-snmp-trap-vars "dnCfmTrapMdLevel.0 {md-level}; dnCfmTrapMdName.0 {maintenance-domain-name}; dnCfmTrapMaName.0 {maintenance-association-name}; dnCfmTrapHighestDefectPri.0 {highest-defect-numeric}";
    leaf highest-defect {
      type enumeration {
        enum DefXconCCM;
        enum DefErrorCCM;
        enum DefRemoteCCM;
        enum DefMACstatus;
        enum DefRDICCM;
      }
      description
        "The highest priority defect detected in the Maintenance Association";
    }
    leaf md-level {
      type uint8 {
        range "0..7";
      }
      description
        "Reported critical link event";
    }
    leaf maintenance-domain-name {
      type string;
      description
        "The name of the Maintenance Domain";
    }
    leaf md-name {
      type string;
      description
        "The Maintenance Domain name";
    }
    leaf maintenance-association-name {
      type string;
      description
        "The name of the Maintenance Association within the MD";
    }
    leaf short-ma-name {
      type string;
      description
        "The Maintenance Association identifier (short-ma-name)";
    }
    leaf action {
      type enumeration {
        enum no-action;
        enum disable-interface;
      }
      description
        "Action to be performed following the defect detection";
    }
    leaf highest-defect-numeric {
      type uint8 {
        range "1..5";
      }
      description
        "The highest priority defect as a numeric value corresponding to IEEE 802.1ag defect priorities";
    }
  }

  notification CFM_DEFECT_CONDITION_CLEARED {
    description
      "All detected defect conditions were cleared in the CFM service.";
    dn-events-extensions:event-severity-level "Info";
    dn-events-extensions:event-message-string "All CFM defects detected in level {md-level} maintenance-domain {maintenance-domain-name} (MD-name {md-name}), maintenance-association {maintenance-association-name} (short-MA-name {short-ma-name}) have been cleared.";
    dn-events-extensions:event-corrective-action-string "This is informational, no corrective action required.";
    dn-events-extensions:event-trigger-component-string "WB Agent";
    dn-events-extensions:event-group "CFM-OAM";
    dn-events-extensions:event-snmp-trap-name "dnCfmFaultAlarmCleared";
    dn-events-extensions:event-snmp-trap-oid "1.3.6.1.4.1.49739.2.15.0.2";
    dn-events-extensions:event-snmp-trap-vars "dnCfmTrapMdLevel.0 {md-level}; dnCfmTrapMdName.0 {maintenance-domain-name}; dnCfmTrapMaName.0 {maintenance-association-name}; dnCfmTrapHighestDefectPri.0 0";
    leaf md-level {
      type uint8 {
        range "0..7";
      }
      description
        "Reported critical link event";
    }
    leaf maintenance-domain-name {
      type string;
      description
        "The name of the Maintenance Domain";
    }
    leaf md-name {
      type string;
      description
        "The Maintenance Domain name";
    }
    leaf maintenance-association-name {
      type string;
      description
        "The name of the Maintenance Association within the MD";
    }
    leaf short-ma-name {
      type string;
      description
        "The Maintenance Association identifier (short-ma-name)";
    }
  }

  notification CFM_MAXIMUM_AUTO_DISCOVERED_RMEPS_LIMIT_REACHED {
    description
      "The number of Connectivity Fault Management (CFM) auto-discovered remote Maintenance association End Points (MEP)s has reached the configured system limit.";
    dn-events-extensions:event-severity-level "Warning";
    dn-events-extensions:event-message-string "The number of CFM auto-discovered remote MEPs has reached the system limit of {limit} dynamically learned remote MEPs";
    dn-events-extensions:event-corrective-action-string "Review the global CFM configuration";
    dn-events-extensions:event-trigger-component-string "WB Agent";
    dn-events-extensions:event-group "CFM-OAM";
    leaf limit {
      type uint32;
      description
        "The maximum limit of auto-discovered remote MEPs in the system";
    }
  }

  notification CFM_MAXIMUM_AUTO_DISCOVERED_RMEPS_LIMIT_CLEARED {
    description
      "The number of Connectivity Fault Management (CFM) auto-discovered remote Maintenance association End Points (MEP)s has moved below the system limit.";
    dn-events-extensions:event-severity-level "Info";
    dn-events-extensions:event-message-string "The number of CFM auto-discovered remote MEPs has moved below the system limit of {limit} dynamically learned remote MEPs";
    dn-events-extensions:event-corrective-action-string "This is informational, no corrective action required.";
    dn-events-extensions:event-trigger-component-string "WB Agent";
    dn-events-extensions:event-group "CFM-OAM";
    leaf limit {
      type uint32;
      description
        "The maximum limit of auto-discovered remote MEPs in the system";
    }
  }

  notification CFM_MAXIMUM_AUTO_DISCOVERED_RMEPS_LIMIT_THRESHOLD_EXCEEDED {
    description
      "The number of Connectivity Fault Management (CFM) auto-discovered remote Maintenance association End Points (MEP)s has crossed the system threshold.";
    dn-events-extensions:event-severity-level "Notice";
    dn-events-extensions:event-message-string "The number of auto-discovered remote MEPs in CFM has exceeded the system threshold of {threshold}%, of the system's maximum limit of {limit} dynamically learned remote MEPs";
    dn-events-extensions:event-corrective-action-string "No corrective action.";
    dn-events-extensions:event-trigger-component-string "WB Agent";
    dn-events-extensions:event-group "CFM-OAM";
    leaf threshold {
      type uint8;
      description
        "Threshold percent";
    }
    leaf limit {
      type uint32;
      description
        "The maximum limit of auto-discovered remote MEPs in the system";
    }
  }

  notification CFM_MAXIMUM_AUTO_DISCOVERED_RMEPS_LIMIT_THRESHOLD_CLEARED {
    description
      "The number of Connectivity Fault Management (CFM) auto-discovered remote Maintenance association End Points (MEP)s has moved below the system threshold.";
    dn-events-extensions:event-severity-level "Info";
    dn-events-extensions:event-message-string "The number of auto-discovered remote MEPs in CFM has moved below the system threshold of {threshold}%, of the system's maximum limit of {limit} dynamically learned remote MEPs";
    dn-events-extensions:event-corrective-action-string "This is informational, no corrective action required.";
    dn-events-extensions:event-trigger-component-string "WB Agent";
    dn-events-extensions:event-group "CFM-OAM";
    leaf threshold {
      type uint8;
      description
        "Threshold percent";
    }
    leaf limit {
      type uint32;
      description
        "The maximum limit of auto-discovered remote MEPs in the system";
    }
  }

  notification CFM_PROACTIVE_TEST_FAILURE {
    description
      "The CFM proactive test has failed due to a threshold violation.";
    dn-events-extensions:event-severity-level "Notice";
    dn-events-extensions:event-message-string "CFM proactive {test-type} test session {session-name} (ID: {session-id}) initiated from MEP {source-mep-id} in MA "
                                            + "{source-ma-name} under MD {source-md-name} in level {source-md-level} has failed due to a violation of the configured {threshold-type-id} threshold "
                                            + "of {threshold-value-and-units}. Recorded value: {calculated-violating-metric-and-units}. Test completed at: {test-end-time}";
    dn-events-extensions:event-corrective-action-string "This is informational, no corrective action required.";
    dn-events-extensions:event-trigger-component-string "WB Agent";
    dn-events-extensions:event-group "CFM-OAM";
    dn-events-extensions:event-snmp-trap-name "dnCfmProactiveTestFailure";
    dn-events-extensions:event-snmp-trap-oid "1.3.6.1.4.1.49739.2.15.0.3";
    dn-events-extensions:event-snmp-trap-vars "dnCfmTrapMdLevel.0 {source-md-level}; dnCfmTrapMdName.0 {source-md-name}; dnCfmTrapMaName.0 {source-ma-name}; "
                                            + "dnCfmTrapMepId.0 {source-mep-id}; dnCfmTrapSessionType.0 {test-type}; dnCfmTrapSessionId.0 {session-id}; "
                                            + "dnCfmTrapThresholdType.0 {threshold-type-id}; dnCfmTrapMeasuredValue.0 {measured-value-raw}";
    leaf test-type {
      type enumeration {
        enum two-way-delay-measurement {
          value 1;
        }
        enum two-way-synthetic-loss-measurement {
          value 2;
        }
      }
      description
        "Type of proactive test that failed (for syslog text).";
    }
    leaf session-name {
      type string;
      description
        "CFM proactive test session name (for syslog text).";
    }
    leaf session-id {
      type uint16;
      description
        "Internal system-generated CFM proactive test session id.";
    }
    leaf source-mep-id {
      type uint16 {
        range "1..8191";
      }
      description
        "Source MEP ID.";
    }
    leaf source-ma-name {
      type string;
      description
        "Source MA name.";
    }
    leaf source-md-name {
      type string;
      description
        "Source MD name.";
    }
    leaf source-md-level {
      type uint8 {
        range "0..7";
      }
      description
        "MD level.";
    }
    leaf threshold-value-and-units {
      type string;
      description
        "Configured threshold value with units for syslog, e.g. '12000 us' or '9590 hundredths-percent (95.90%)'.";
    }
    leaf calculated-violating-metric-and-units {
      type string;
      description
        "Measured violating value with units for syslog, e.g. '15340 us' or '1200 hundredths-percent (12.00%)'.";
    }
    leaf test-end-time {
      type string;
      description
        "Time the test completed (display-friendly).";
    }
    leaf threshold-type-id {
      type enumeration {
        enum frame-delay-two-way-min {
          value 1;
        }
        enum frame-delay-two-way-avg {
          value 2;
        }
        enum frame-delay-two-way-max {
          value 3;
        }
        enum ifdv-two-way-avg {
          value 4;
        }
        enum ifdv-two-way-max {
          value 5;
        }
        enum successRatePercent {
          value 6;
        }
        enum frame-loss-near-end-percentage {
          value 7;
        }
        enum frame-loss-far-end-percentage {
          value 8;
        }
      }
      description
        "Raw enum for dnCfmTrapThresholdType:
         1=frameDelayTwoWayMin, 2=frameDelayTwoWayAvg, 3=frameDelayTwoWayMax,
         4=ifdvTwoWayAvg, 5=ifdvTwoWayMax, 6=successRatePercent,
         7=frameLossNearEndPercent, 8=frameLossFarEndPercent.";
    }
    leaf measured-value-raw {
      type uint32;
      description
        "Raw value for dnCfmTrapMeasuredValue (no units):
         - If threshold-type-id in {1..5}: microseconds.
         - If threshold-type-id in {6..8}: hundredths of a percent (e.g., 80.30% => 8030).";
    }
  }

  // Flow-monitor (IPFIX/Netflow) system-events

  notification FLOW_MONITORING_CACHE_SIZE_THRESHOLD_EXCEEDED {
    description
      "The number of flows in the flow-cache table for each NCP has exceeded the configured threshold. If the flow-cache table size reaches 100%, the flow entries will be aged out.";
    dn-events-extensions:event-severity-level "Notice";
    dn-events-extensions:event-message-string "Number of flows in the flow-cache table per NCP {ncp-id} has exceeded configured threshold of {threshold} - {num-of-flow-entries}";
    dn-events-extensions:event-corrective-action-string "None";
    dn-events-extensions:event-trigger-component-string "WB";
    dn-events-extensions:event-group "System";
    leaf ncp-id {
      type uint16;
      description
        "NCP ID";
    }
    leaf threshold {
      type uint8;
      description
        "Threshold percentage";
    }
    leaf num-of-flow-entries {
      type uint8;
      description
        "Number of flow entries in flow-cache table";
    }
  }

  notification FLOW_MONITORING_CACHE_SIZE_THRESHOLD_CLEARED {
    description
      "The number of flows in the flow-cache table for the NCP is below the configured threshold.";
    dn-events-extensions:event-severity-level "Info";
    dn-events-extensions:event-message-string "Number of flows in the flow-cache table for NCP {ncp-id} is below the configured system threshold {threshold}% of the limit ({limit}). The number of flows are ({num-of-flow-entries})";
    dn-events-extensions:event-corrective-action-string "This is informational, no corrective action required.";
    dn-events-extensions:event-trigger-component-string "WB";
    dn-events-extensions:event-group "System";
    leaf ncp-id {
      type uint16;
      description
        "NCP ID";
    }
    leaf threshold {
      type uint8;
      description
        "Threshold percentage";
    }
    leaf limit {
      type uint8;
      description
        "Maximum number of flow entries in flow-cache table";
    }
    leaf num-of-flow-entries {
      type uint8;
      description
        "Number of flow entries in flow-cache table";
    }
  }

  notification FLOW_MONITORING_CACHE_SIZE_LIMIT_REACHED {
    description
      "The number of flows in the flow-cache table for the NCP has reached the system limit. Adding new flow entries to the flow-cache table will cause the longest idle flow entries to be aggressively timed out.";
    dn-events-extensions:event-severity-level "Warning";
    dn-events-extensions:event-message-string "Number of flows in the flow-cache table for NCP {ncp-id} has reached the system limit {limit}, the current rate of sampled packets is {packet-rate}";
    dn-events-extensions:event-corrective-action-string "No corrective action.";
    dn-events-extensions:event-trigger-component-string "WB";
    dn-events-extensions:event-group "System";
    leaf ncp-id {
      type uint16;
      description
        "NCP ID";
    }
    leaf limit {
      type uint8;
      description
        "Maximum number of flow entries in flow-cache table";
    }
    leaf packet-rate {
      type uint16;
      description
        "Rate of sampled packets at the moment of system-event generations";
    }
  }

  notification FLOW_MONITORING_CACHE_SIZE_LIMIT_CLEARED {
    description
      "The number of flows in the flow-cache table for the NCP is below the system limit.";
    dn-events-extensions:event-severity-level "Info";
    dn-events-extensions:event-message-string "Number of flows in the flow-cache table for NCP {ncp-id} is below the system limit {limit}, the current rate of sampled packets is {packet-rate}";
    dn-events-extensions:event-corrective-action-string "This is informational, no corrective action required.";
    dn-events-extensions:event-trigger-component-string "WB";
    dn-events-extensions:event-group "System";
    leaf ncp-id {
      type uint16;
      description
        "NCP ID";
    }
    leaf limit {
      type uint8;
      description
        "Maximum number of flow entries in flow-cache table";
    }
    leaf packet-rate {
      type uint16;
      description
        "Rate of sampled packets at the moment of system-event generations";
    }
  }

  notification FLOW_MONITORING_SAMPLING_RATE_LIMIT_REACHED {
    description
      "The rate of sampled flow packets for the NCP has reached the system limit. Some sampled packets will not be processed.";
    dn-events-extensions:event-severity-level "Warning";
    dn-events-extensions:event-message-string "Rate of sampled flow packets for NCP {ncp-id} has reached the system limit of rate {limit}";
    dn-events-extensions:event-corrective-action-string "No corrective action.";
    dn-events-extensions:event-trigger-component-string "WB";
    dn-events-extensions:event-group "System";
    leaf ncp-id {
      type uint16;
      description
        "NCP ID";
    }
    leaf limit {
      type uint8;
      description
        "Rate of sampled packets for flow monitoring";
    }
  }

  notification FLOW_MONITORING_SAMPLING_RATE_LIMIT_CLEARED {
    description
      "The rate of sampled flow packets for the NCP is below the system limit.";
    dn-events-extensions:event-severity-level "Info";
    dn-events-extensions:event-message-string "Rate of sampled flow packets for NCP {ncp-id} is below the system limit of rate {limit}";
    dn-events-extensions:event-corrective-action-string "This is informational, no corrective action required.";
    dn-events-extensions:event-trigger-component-string "WB";
    dn-events-extensions:event-group "System";
    leaf ncp-id {
      type uint16;
      description
        "NCP ID";
    }
    leaf limit {
      type uint8;
      description
        "Rate of sampled packets for flow monitoring";
    }
  }

  notification FLOW_MONITORING_CACHE_OVERFLOWS_DROPPED {
    description
      "Some flows that were removed from the cache (due to timeout or cache flush) could not be exported since cache-rate-limit was exceeded.";
    dn-events-extensions:event-severity-level "Warning";
    dn-events-extensions:event-message-string "Timeout flows were not exported on NCP {ncp-id} due to cache-rate-limit exceed. The accumulative number of cache overflows on the NCP is {overflow-counter}";
    dn-events-extensions:event-corrective-action-string "This is informational, no corrective action required.";
    dn-events-extensions:event-trigger-component-string "WB";
    dn-events-extensions:event-group "System";
    leaf ncp-id {
      type uint16;
      description
        "NCP ID";
    }
    leaf overflow-counter {
      type uint32;
      description
        "Total number of overflows in the cache";
    }
  }

  notification FLOW_MONITORING_CACHE_OVERLOADED_DROPPED {
    description
      "Some flows that were removed from the cache (due to timeout or cache flush) could not be exported due to system overload on the from-us direction.";
    dn-events-extensions:event-severity-level "Warning";
    dn-events-extensions:event-message-string "Timeout flows were not exported on NCP {ncp-id} due to system overload on the from-us direction, the reason is {reason}. The accumulative number of cache overloaded dropped flows on the NCP is {overloaded-drop}";
    dn-events-extensions:event-corrective-action-string "This is informational, no corrective action required.";
    dn-events-extensions:event-trigger-component-string "WB";
    dn-events-extensions:event-group "System";
    leaf ncp-id {
      type uint16;
      description
        "NCP ID";
    }
    leaf overloaded-drop {
      type uint32;
      description
        "Total number of dropped exported flows due to overloaded system on the from-us direction";
    }
    leaf reason {
      type string;
      description
        "The reason for system overload on the from-us direction";
    }
  }

  // BFD events

  notification BFD_STATE_UP {
    description
      "The BFD session changed to an 'up' state.";
    dn-events-extensions:event-severity-level "Info";
    dn-events-extensions:event-message-string "BFD session {local-address} to {remote-address} has changed state from {old-state} to UP. BFD session information: "
                                            + "local discriminator {local-discriminator}, remote-discriminator {remote-discriminator}, "
                                            + "session diagnostic {session-diagnostic}, protecting {clients}";
    dn-events-extensions:event-corrective-action-string "This is informational, no corrective action required.";
    dn-events-extensions:event-trigger-component-string "BFD";
    dn-events-extensions:event-group "BFD";
    dn-events-extensions:event-snmp-trap-name "dnBfdSessionUp";
    dn-events-extensions:event-snmp-trap-oid "1.3.6.1.4.1.49739.2.3.0.1";
    dn-events-extensions:event-snmp-trap-vars "dnBfdVersion.0 {bfd-version}; dnAddressType.0 {address-type}; dnLocalAddress.0 CONVERT inetAddr({address-type}) {local-address}; dnRemoteAddress.0 CONVERT inetAddr({address-type}) {remote-address}; dnRemotePort.0 {remote-port}; dnLocalDiscriminator.0 {local-discriminator}; dnRemoteDiscriminator.0 {remote-discriminator}; dnClients.0 {clients}; dnSessionDiagnostic.0 {session-diagnostic}";
    leaf old-state {
      description
        "Session old state, Down, Init, Admin-Down";
      type enumeration {
        enum Down;
        enum Init;
        enum Admin-Down;
      }
    }
    leaf clients {
      description
        "All registered clients for the BFD session, e.g BGP, static, interface,...";
      type string;
    }
    leaf bfd-version {
      description
        "BFD protocol version in use";
      type uint32;
    }
    leaf address-type {
      description
        "This object specifies the IP address type of the source IP
         address of this BFD session.  The value of unknown(0) is
         allowed only when the session is singleHop(1) and the
         source IP address of this BFD session is derived from
         the outgoing interface, or when the BFD session is not
         associated with a specific interface.  If any other
         unsupported values are attempted in a set operation, the
         agent MUST return an inconsistentValue error.";
      type enumeration {
        enum unknown {
          value 0;
        }
        enum ipv4 {
          value 1;
        }
        enum ipv6 {
          value 2;
        }
        enum dns {
          value 16;
        }
      }
    }
    leaf local-address {
      description
        "BFD IP address on local system";
      type string;
    }
    leaf remote-address {
      description
        "BFD IP address on remote system";
      type string;
    }
    leaf remote-port {
      description
        "BFD UDP port number on remote system";
      type uint32 {
        range "0..65535";
      }
    }
    leaf local-discriminator {
      description
        "A unique, nonzero discriminator value generated by the transmitting system";
      type uint32;
    }
    leaf remote-discriminator {
      description
        "A unique discriminator value received from remote system, if unknown , set to 0";
      type uint32;
    }
    leaf session-diagnostic {
      description
        "Session diagnostic code from last received bfd msg for dnBfdObjects - should be (0) for bfdSessionDown - should be either (4),(5),(6),(7)";
      type enumeration {
        enum no-diagnostic {
          value 0;
        }
        enum control-detection-time-expired {
          value 1;
        }
        enum echo-function-failed {
          value 2;
        }
        enum neighbor-signaled-session-down {
          value 3;
        }
        enum forwarding-plane-reset {
          value 4;
        }
        enum path-down {
          value 5;
        }
        enum concatenated-path-down {
          value 6;
        }
        enum administratively-down {
          value 7;
        }
        enum reverse-concatenated-path-down {
          value 8;
        }
        enum mis-connectivity-defect {
          value 9;
        }
      }
    }
  }

  notification BFD_STATE_DOWN {
    description
      "The BFD session changed to a 'down' or 'Admin-down' state.";
    dn-events-extensions:event-severity-level "Warning";
    dn-events-extensions:event-message-string "BFD session {local-address} to {remote-address} has changed state from {old-state} to {new-state}. BFD session information: "
                                            + "local discriminator {local-discriminator}, remote-discriminator {remote-discriminator}, "
                                            + "session diagnostic {session-diagnostic}, protecting {clients}";
    dn-events-extensions:event-corrective-action-string "Check the connectivity to the neighbor.";
    dn-events-extensions:event-trigger-component-string "BFD";
    dn-events-extensions:event-group "BFD";
    dn-events-extensions:event-snmp-trap-name "dnBfdSessionDown";
    dn-events-extensions:event-snmp-trap-oid "1.3.6.1.4.1.49739.2.3.0.2";
    dn-events-extensions:event-snmp-trap-vars "dnBfdVersion.0 {bfd-version}; dnAddressType.0 {address-type}; dnLocalAddress.0 CONVERT inetAddr({address-type}) {local-address}; dnRemoteAddress.0 CONVERT inetAddr({address-type}) {remote-address}; dnRemotePort.0 {remote-port}; dnLocalDiscriminator.0 {local-discriminator}; dnRemoteDiscriminator.0 {remote-discriminator}; dnClients.0 {clients}; dnSessionDiagnostic.0 {session-diagnostic}";
    leaf old-state {
      description
        "Session old state, Down, Init, Admin-Down, Up";
      type enumeration {
        enum Down;
        enum Init;
        enum Admin-Down;
        enum Up;
      }
    }
    leaf new-state {
      description
        "Session new state, Down or Admin-Down";
      type enumeration {
        enum Down;
        enum Admin-Down;
      }
    }
    leaf clients {
      description
        "All registered clients for the BFD session, e.g BGP, static, interface,...";
      type string;
    }
    leaf bfd-version {
      description
        "BFD protocol version in use.";
      type uint32;
    }
    leaf address-type {
      description
        "This object specifies the IP address type of the source IP
         address of this BFD session.  The value of unknown(0) is
         allowed only when the session is singleHop(1) and the
         source IP address of this BFD session is derived from
         the outgoing interface, or when the BFD session is not
         associated with a specific interface.  If any other
         unsupported values are attempted in a set operation, the
         agent MUST return an inconsistentValue error.";
      type enumeration {
        enum unknown {
          value 0;
        }
        enum ipv4 {
          value 1;
        }
        enum ipv6 {
          value 2;
        }
        enum dns {
          value 16;
        }
      }
    }
    leaf local-address {
      description
        "BFD IP address on local system";
      type string;
    }
    leaf remote-address {
      description
        "BFD IP address on remote system";
      type string;
    }
    leaf remote-port {
      description
        "BFD UDP port number on remote system";
      type uint32 {
        range "0..65535";
      }
    }
    leaf local-discriminator {
      description
        "A unique, nonzero discriminator value generated by the transmitting system";
      type uint32;
    }
    leaf remote-discriminator {
      description
        "A unique discriminator value received from remote system, if unknown , set to 0";
      type uint32;
    }
    leaf session-diagnostic {
      description
        "Session diagnostic code from last received bfd msg for dnBfdObjects - should be (0) for bfdSessionDown - should be either (4),(5),(6),(7)";
      type enumeration {
        enum no-diagnostic {
          value 0;
        }
        enum control-detection-time-expired {
          value 1;
        }
        enum echo-function-failed {
          value 2;
        }
        enum neighbor-signaled-session-down {
          value 3;
        }
        enum forwarding-plane-reset {
          value 4;
        }
        enum path-down {
          value 5;
        }
        enum concatenated-path-down {
          value 6;
        }
        enum administratively-down {
          value 7;
        }
        enum reverse-concatenated-path-down {
          value 8;
        }
        enum mis-connectivity-defect {
          value 9;
        }
      }
    }
  }

  notification BFD_INTERNAL_ERROR {
    description
      "The BFD process failed due to an internal error.";
    dn-events-extensions:event-severity-level "Error";
    dn-events-extensions:event-message-string "BFD encountered an error: {error-type}, {error-message}. BFD location {bfd-location}";
    dn-events-extensions:event-corrective-action-string "Copy the error message and contact Customer Support.";
    dn-events-extensions:event-trigger-component-string "BFD";
    dn-events-extensions:event-group "BFD";
    leaf error-type {
      type string;
      description
        "Error group type";
    }
    leaf error-message {
      type string;
      description
        "Error description";
    }
    leaf bfd-location {
      description
        "Which node runs the BFD session. e.g NCP <id>";
      type string;
    }
  }

  notification BFD_MAXIMUM_SESSIONS_LIMIT_REACHED {
    description
      "The number of BFD sessions have reached the maximum system limit of supported sessions.";
    dn-events-extensions:event-severity-level "Warning";
    dn-events-extensions:event-message-string "Number of BFD sessions has reached system limit of {limit} sessions. The current number of sessions is {session-number}";
    dn-events-extensions:event-corrective-action-string "Remove low priority sessions.";
    dn-events-extensions:event-trigger-component-string "BFD";
    dn-events-extensions:event-group "BFD";
    leaf limit {
      type uint16;
      description
        "Maximum number of sessions";
    }
    leaf session-number {
      type uint16;
      description
        "Current number of BFD sessions";
    }
  }

  notification BFD_MAXIMUM_SESSIONS_LIMIT_CLEARED {
    description
      "The number of BFD sessions have moved below the system limit.";
    dn-events-extensions:event-severity-level "Info";
    dn-events-extensions:event-message-string "Number of BFD sessions is below the system limit of {limit}. The current number of sessions is {session-number}";
    dn-events-extensions:event-corrective-action-string "This is informational, no corrective action required.";
    dn-events-extensions:event-trigger-component-string "bfd";
    dn-events-extensions:event-group "BFD";
    leaf limit {
      type uint16;
      description
        "Maximum number of sessions";
    }
    leaf session-number {
      type uint16;
      description
        "Current number of BFD sessions";
    }
  }

  notification BFD_MAXIMUM_SESSIONS_THRESHOLD_EXCEEDED {
    description
      "The number of BFD sessions have crossed the system threshold for the number of supported sessions.";
    dn-events-extensions:event-severity-level "Notice";
    dn-events-extensions:event-message-string "Number of BFD sessions have crossed the system threshold {threshold}% of the limit ({limit}). The current number of BFD sessions is {session-number}";
    dn-events-extensions:event-corrective-action-string "Remove low priority sessions.";
    dn-events-extensions:event-trigger-component-string "BFD";
    dn-events-extensions:event-group "BFD";
    leaf threshold {
      type uint8;
      description
        "Limit percent threshold";
    }
    leaf limit {
      type uint16;
      description
        "Maximum number of sessions";
    }
    leaf session-number {
      type uint16;
      description
        "Current number of BFD sessions";
    }
  }

  notification BFD_MAXIMUM_SESSIONS_THRESHOLD_CLEARED {
    description
      "The number of BFD sessions have moved below the system threshold of supported sessions.";
    dn-events-extensions:event-severity-level "Info";
    dn-events-extensions:event-message-string "Number of BFD sessions is below the system threshold {threshold}% of the limit ({limit}). The number of BFD sessions is {session-number}";
    dn-events-extensions:event-corrective-action-string "This is informational, no corrective action required.";
    dn-events-extensions:event-trigger-component-string "BFD";
    dn-events-extensions:event-group "BFD";
    leaf threshold {
      type uint8;
      description
        "Limit percent threshold";
    }
    leaf limit {
      type uint16;
      description
        "Maximum number of sessions";
    }
    leaf session-number {
      type uint16;
      description
        "Current number of BFD sessions";
    }
  }

  notification BFD_SUPPRESSED {
    description
      "The BFD session have been suppressed due to BFD dampening.";
    dn-events-extensions:event-severity-level "Info";
    dn-events-extensions:event-message-string "BFD session {local_address} to {remote_address} have been suppressed. BFD session information: local discriminator {local_discriminator}, remote_discriminator {remote_discriminator}, protecting {clients}";
    dn-events-extensions:event-corrective-action-string "No corrective action is required.";
    dn-events-extensions:event-trigger-component-string "BFD";
    dn-events-extensions:event-group "BFD";
    leaf clients {
      description
        "All registered clients for the BFD session, e.g BGP, static, interface,...";
      type string;
    }
    leaf local-address {
      description
        "BFD IP address on local system";
      type string;
    }
    leaf remote-address {
      description
        "BFD IP address on remote system";
      type string;
    }
    leaf local-discriminator {
      description
        "A unique, nonzero discriminator value generated by the transmitting system";
      type uint32;
    }
    leaf remote-discriminator {
      description
        "A unique discriminator value received from remote system, if unknown , set to 0";
      type uint32;
    }
  }

  notification BFD_SUPPRESS_ENDED {
    description
      "BFD change suppression has ended because either the BFD dampening penalty decay is below the reuse threshold, the maximum suppression timer has expired, or the penalty was manually cleared.";
    dn-events-extensions:event-severity-level "Info";
    dn-events-extensions:event-message-string "BFD session {local_address} to {remote_address} suppression ended, due to {suppression_end_reason}. BFD session information: local discriminator {local_discriminator}, remote_discriminator {remote_discriminator}, protecting {clients}";
    dn-events-extensions:event-corrective-action-string "No corrective action is required.";
    dn-events-extensions:event-trigger-component-string "BFD";
    dn-events-extensions:event-group "BFD";
    leaf clients {
      description
        "All registered clients for the BFD session, e.g BGP, static, interface,...";
      type string;
    }
    leaf local-address {
      description
        "BFD IP address on local system";
      type string;
    }
    leaf remote-address {
      description
        "BFD IP address on remote system";
      type string;
    }
    leaf local-discriminator {
      description
        "A unique, nonzero discriminator value generated by the transmitting system";
      type uint32;
    }
    leaf remote-discriminator {
      description
        "A unique discriminator value received from remote system, if unknown , set to 0";
      type uint32;
    }
    leaf suppression-end-reason {
      type enumeration {
        enum penalty-decayed-below-reuse-threshold {
          value 0;
        }
        enum max-suppress-timer-expired {
          value 1;
        }
        enum penalty-cleared-manually {
          value 2;
        }
        enum zero-reset {
          value 3;
        }
      }
      description
        "BFD state suppress end reasons";
    }
  }

  notification DNS_SERVER_CONFIG {
    description
      "A DNS server was added/removed to/from the system.";
    dn-events-extensions:event-severity-level "Info";
    dn-events-extensions:event-message-string "User {user-name} has {action} DNS server {server-address} on VRF {vrf-name}, server's admin-state {admin-state}";
    dn-events-extensions:event-corrective-action-string "This is informational, no corrective action required.";
    dn-events-extensions:event-trigger-component-string "Transaction-manager";
    dn-events-extensions:event-group "System";
    leaf user-name {
      type string;
      description
        "User-name of the user who add/removed DNS server";
    }
    leaf action {
      type string;
      description
        "Configuration action (added/removed)";
    }
    leaf server-address {
      type string;
      description
        "IP address of DNS server that was added/removed";
    }
    leaf vrf-name {
      type string;
      description
        "Name of the VRF";
    }
    leaf admin-state {
      description
        "DNS server admin-state";
      type enumeration {
        enum disabled;
        enum enabled;
      }
    }
  }

  // LDP System events and SNMP traps

  notification LDP_HELLO_ADJACENCY_UP {
    description
      "LDP received discovery hellos on the listed interface. Adjacency has moved to an 'up' state.";
    dn-events-extensions:event-severity-level "Info";
    dn-events-extensions:event-message-string "LDP interface adjacency on interface {if-name} is up";
    dn-events-extensions:event-corrective-action-string "This is informational, no corrective action required.";
    dn-events-extensions:event-trigger-component-string "LDP";
    dn-events-extensions:event-group "LDP";
    leaf if-name {
      type string;
      description
        "Interface name";
    }
  }

  notification LDP_HELLO_ADJACENCY_DOWN {
    description
      "LDP stopped receiving discovery hellos on the listed interface. Adjacency has moved to 'down' state.";
    dn-events-extensions:event-severity-level "Warning";
    dn-events-extensions:event-message-string "LDP interface adjacency on interface {if-name} is down";
    dn-events-extensions:event-corrective-action-string "No corrective action required.";
    dn-events-extensions:event-trigger-component-string "LDP";
    dn-events-extensions:event-group "LDP";
    leaf if-name {
      type string;
      description
        "Interface name";
    }
  }

  notification LDP_TARGETED_HELLO_ADJACENCY_UP {
    description
      "LDP has received discovery hellos from the targeted side. Adjacency has moved to an 'up' state.";
    dn-events-extensions:event-severity-level "Info";
    dn-events-extensions:event-message-string "Targeted LDP adjacency to {ip-address} is up";
    dn-events-extensions:event-corrective-action-string "This is informational, no corrective action required.";
    dn-events-extensions:event-trigger-component-string "LDP";
    dn-events-extensions:event-group "LDP";
    leaf ip-address {
      type string;
      description
        "Targeted ip-address";
    }
  }

  notification LDP_TARGETED_HELLO_ADJACENCY_DOWN {
    description
      "LDP has stopped receiving discovery hellos from the targeted side. Adjacency has moved to a 'down' state.";
    dn-events-extensions:event-severity-level "Warning";
    dn-events-extensions:event-message-string "Targeted LDP adjacency to {ip-address} is down";
    dn-events-extensions:event-corrective-action-string "No corrective action required.";
    dn-events-extensions:event-trigger-component-string "LDP";
    dn-events-extensions:event-group "LDP";
    leaf ip-address {
      type string;
      description
        "Targeted ip-address";
    }
  }

  notification LDP_TARGETED_HELLO_DISCARDED {
    description
      "The received targeted hello was discarded.";
    dn-events-extensions:event-severity-level "Notice";
    dn-events-extensions:event-message-string "Discarded received targeted hello from {ip-address}";
    dn-events-extensions:event-corrective-action-string "Check if the targeted accept message is enabled and that the peer is allowed according to the allowed-peer filter list.";
    dn-events-extensions:event-trigger-component-string "LDP";
    dn-events-extensions:event-group "LDP";
    leaf ip-address {
      type string;
      description
        "Targeted ip-address";
    }
  }

  notification LDP_IGP_SYNC {
    description
      "This event is triggered when LDP synchronization with IGP has either started or completed.";
    dn-events-extensions:event-severity-level "Info";
    dn-events-extensions:event-message-string "LDP synchronization. Status: {sync-state} on interface: {if-name}. Sync delay time: {sync-delay}";
    dn-events-extensions:event-corrective-action-string "This is informational, no corrective action required.";
    dn-events-extensions:event-trigger-component-string "LDP";
    dn-events-extensions:event-group "LDP";
    leaf sync-state {
      description
        "The synchronization state";
      type enumeration {
        enum in-progress {
          value 1;
        }
        enum completed {
          value 2;
        }
      }
    }
    leaf if-name {
      type string;
      description
        "Interface name";
    }
    leaf sync-delay {
      type uint16;
      description
        "Synchronization delay in seconds";
    }
  }

  notification LDP_IGP_TUNNELING_SYNC {
    description
      "This event is triggered when LDP synchronization with IGP that is using RSVP tunnels, has either started or completed.";
    dn-events-extensions:event-severity-level "Info";
    dn-events-extensions:event-message-string "LDP IGP-Tunneling synchronization. Status: {sync-state} for {tunnel-origin} tunnel {tunnel-name} with destination address {ipv4-address}. Sync delay time: {sync-delay}";
    dn-events-extensions:event-corrective-action-string "This is informational, no corrective action required.";
    dn-events-extensions:event-trigger-component-string "LDP";
    dn-events-extensions:event-group "LDP";
    leaf sync-state {
      description
        "The synchronization state";
      type enumeration {
        enum in-progress {
          value 1;
        }
        enum completed {
          value 2;
        }
      }
    }
    leaf tunnel-origin {
      description
        "origin of the tunnel used for ldp tunneling, either RSVP or SR-TE";
      type enumeration {
        enum RSVP;
        enum SR-TE;
      }
    }
    leaf tunnel-name {
      description
        "the name of the head-end rsvp tunnel enabled for ldp-sync for which no ldp session exist with tunnel destination";
      type string;
    }
    leaf ipv4-address {
      type string;
      description
        "Targeted ip-address";
    }
    leaf sync-delay {
      type uint16;
      description
        "synchronization delay in seconds";
    }
  }

  notification LDP_SESSION_UP {
    description
      "The LDP session state has moved to an 'up' state.";
    dn-events-extensions:event-severity-level "Info";
    dn-events-extensions:event-message-string "LDP session with neighbor {neighbor-ip-address} is up. The TCP port is {session-tcp-port}";
    dn-events-extensions:event-corrective-action-string "This is informational, no corrective action required.";
    dn-events-extensions:event-trigger-component-string "LDP";
    dn-events-extensions:event-group "LDP";
    dn-events-extensions:event-snmp-trap-name "mplsLdpSessionUp";
    dn-events-extensions:event-snmp-trap-oid "1.3.6.1.2.1.10.166.4.0.3";
    dn-events-extensions:event-snmp-trap-vars "mplsLdpSessionState.0 {ldp-session-state}; mplsLdpSessionDiscontinuityTime.0 {session-discontinuity-time}; mplsLdpSessionStatsUnknownMesTypeErrors.0 {session-stats-unknown-mes-type-errors}; mplsLdpSessionStatsUnknownTlvErrors.0 {session-stats-unknown-tlv-errors}";
    leaf neighbor-ip-address {
      type string;
      description
        "Neighbor IP address e.g. 1.2.3.4";
    }
    leaf session-tcp-port {
      type uint16;
      description
        "The neighbor's LDP session TCP port";
    }
    leaf ldp-session-state {
      description
        "The current state of the session, all of the
         states 1 to 5 are based on the state machine for session negotiation behavior";
      type enumeration {
        enum nonexistent {
          value 1;
        }
        enum initialized {
          value 2;
        }
        enum openrec {
          value 3;
        }
        enum opensent {
          value 4;
        }
        enum operational {
          value 5;
        }
      }
    }
    leaf session-discontinuity-time {
      type uint32;
      description
        "The sysUpTime (in hundredths of a second) on the most recent occasion at which any one or more of this LDP session's counters
         suffered a discontinuity";
    }
    leaf session-stats-unknown-mes-type-errors {
      type uint32;
      description
        "This object counts the number of Unknown Message Type
         Errors detected by this LSR/LER during this session.
         Discontinuities in the value of this counter can occur
         at reinitialization of the management system, and at
         other times as indicated by the value of
         mplsLdpSessionDiscontinuityTime";
    }
    leaf session-stats-unknown-tlv-errors {
      type uint32;
      description
        "This object counts the number of Unknown TLV Errors
         detected by this LSR/LER during this session.
         Discontinuities in the value of this counter can occur
         at reinitialization of the management system, and at
         other times as indicated by the value of
         mplsLdpSessionDiscontinuityTime";
    }
  }

  notification LDP_SESSION_DOWN {
    description
      "The LDP session has moved to a 'down' state.";
    dn-events-extensions:event-severity-level "Warning";
    dn-events-extensions:event-message-string "LDP session with neighbor {neighbor-ip-address} is down. The TCP port is {session-tcp-port}";
    dn-events-extensions:event-corrective-action-string "No corrective action.";
    dn-events-extensions:event-trigger-component-string "LDP";
    dn-events-extensions:event-group "LDP";
    dn-events-extensions:event-snmp-trap-name "mplsLdpSessionDown";
    dn-events-extensions:event-snmp-trap-oid "1.3.6.1.2.1.10.166.4.0.4";
    dn-events-extensions:event-snmp-trap-vars "mplsLdpSessionState.0 {ldp-session-state}; mplsLdpSessionDiscontinuityTime.0 {session-discontinuity-time}; mplsLdpSessionStatsUnknownMesTypeErrors.0 {session-stats-unknown-mes-type-errors}; mplsLdpSessionStatsUnknownTlvErrors.0 {session-stats-unknown-tlv-errors}";
    leaf neighbor-ip-address {
      type string;
      description
        "Neighbor IP address e.g. 1.2.3.4";
    }
    leaf session-tcp-port {
      type uint16;
      description
        "The neighbor's LDP session TCP port";
    }
    leaf ldp-session-state {
      description
        "The current state of the session, all of the
         states 1 to 5 are based on the state machine for session negotiation behavior";
      type enumeration {
        enum nonexistent {
          value 1;
        }
        enum initialized {
          value 2;
        }
        enum openrec {
          value 3;
        }
        enum opensent {
          value 4;
        }
        enum operational {
          value 5;
        }
      }
    }
    leaf session-discontinuity-time {
      type uint32;
      description
        "The sysUpTime (in hundredths of a second) on the most recent occasion at which any one or more of this LDP session's counters
         suffered a discontinuity";
    }
    leaf session-stats-unknown-mes-type-errors {
      type uint32;
      description
        "This object counts the number of Unknown Message Type
         Errors detected by this LSR/LER during this session.
         Discontinuities in the value of this counter can occur
         at reinitialization of the management system, and at
         other times as indicated by the value of
         mplsLdpSessionDiscontinuityTime";
    }
    leaf session-stats-unknown-tlv-errors {
      type uint32;
      description
        "This object counts the number of Unknown TLV Errors
         detected by this LSR/LER during this session.
         Discontinuities in the value of this counter can occur
         at reinitialization of the management system, and at
         other times as indicated by the value of
         mplsLdpSessionDiscontinuityTime";
    }
  }

  notification LDP_NSR_RECOVERY_START {
    description
      "The system has started LDP Non-Stop Routing recovery due to a restart of the ldpd process.";
    dn-events-extensions:event-severity-level "Info";
    dn-events-extensions:event-message-string "ldpd process is starting a Non-Stop Routing recovery attempt due to process restart";
    dn-events-extensions:event-corrective-action-string "This is informational, no corrective action required.";
    dn-events-extensions:event-trigger-component-string "LDP";
    dn-events-extensions:event-group "LDP";
  }

  notification LDP_NSR_RECOVERED {
    description
      "The system performed an LDP Non-Stop Routing recovery due to a restart of the ldpd process.";
    dn-events-extensions:event-severity-level "Notice";
    dn-events-extensions:event-message-string "LDP Non-Stop Routing recovery was performed due to a restart of the ldpd process";
    dn-events-extensions:event-corrective-action-string "This is informational, no corrective action required.";
    dn-events-extensions:event-trigger-component-string "LDP";
    dn-events-extensions:event-group "LDP";
  }

  notification LDP_NSR_RECOVERY_FAILED {
    description
      "The LDP process failed to recover in Non-Stop Routing mode.";
    dn-events-extensions:event-severity-level "Warning";
    dn-events-extensions:event-message-string "LDP process failed to recover in Non-Stop Routing mode";
    dn-events-extensions:event-corrective-action-string "Verify NSR readiness prior to the failure event.";
    dn-events-extensions:event-trigger-component-string "ldp";
    dn-events-extensions:event-group "LDP";
  }

  notification LDP_NSR_DB_NOT_SYNC {
    description
      "The standby NCC LDP Non-Stop Routing database is not synchronized. LDP will not recover in Non-Stop Routing mode if a system switchover occurs.";
    dn-events-extensions:event-severity-level "Warning";
    dn-events-extensions:event-message-string "Standby NCC LDP NSR database is not synchronized. LDP will not recover in Non-Stop Routing mode if a system switchover occurs";
    dn-events-extensions:event-corrective-action-string "Verify connectivity to the standby NCC.";
    dn-events-extensions:event-trigger-component-string "ldp";
    dn-events-extensions:event-group "LDP";
  }

  notification LDP_NSR_DB_SYNC {
    description
      "The standby NCC LDP Non-Stop Routing database is synchronized.";
    dn-events-extensions:event-severity-level "Info";
    dn-events-extensions:event-message-string "Standby NCC LDP NSR database is synchronized";
    dn-events-extensions:event-corrective-action-string "This is informational, no corrective action required.";
    dn-events-extensions:event-trigger-component-string "ldp";
    dn-events-extensions:event-group "LDP";
  }

  // Event-manager events

  notification EVENT_MANAGER_EVENT_POLICY_TRIGGERED {
    description
      "Event manager triggered event-policy execution.";
    dn-events-extensions:event-severity-level "Notice";
    dn-events-extensions:event-message-string "event-policy {policy-name} was executed with user {user-name} privileges after matching system event {event-name} with attribute {attribute-name}.";
    dn-events-extensions:event-corrective-action-string "No corrective action.";
    dn-events-extensions:event-trigger-component-string "EEM";
    dn-events-extensions:event-group "Management";
    leaf policy-name {
      type string;
      description
        "The name of the policy.";
    }
    leaf user-name {
      type string;
      description
        "The user-name that is used by the policy.";
    }
    leaf event-name {
      type string;
      description
        "The system event that triggers the policy.";
    }
    leaf attribute-name {
      type string;
      description
        "The attribute name that the script receives.";
    }
  }

  notification EVENT_MANAGER_EVENT_POLICY_CONFIG_CHANGE_COMMITTED {
    description
      "Event manager triggered configuration change.";
    dn-events-extensions:event-severity-level "Info";
    dn-events-extensions:event-message-string "Configuration change successful: while executing event-policy {policy-name} with user {user-name} privileges.";
    dn-events-extensions:event-corrective-action-string "No corrective action.";
    dn-events-extensions:event-trigger-component-string "EEM";
    dn-events-extensions:event-group "Management";
    leaf policy-name {
      type string;
      description
        "The name of the policy.";
    }
    leaf user-name {
      type string;
      description
        "The user-name that is used by the policy.";
    }
  }

  notification EVENT_MANAGER_EVENT_POLICY_CONFIG_CHANGE_FAILED {
    description
      "Event manager failed to commit configuration change.";
    dn-events-extensions:event-severity-level "Error";
    dn-events-extensions:event-message-string "Configuration change failed: while executing event-policy {policy-name} with user {user-name} privileges.";
    dn-events-extensions:event-corrective-action-string "Check the embedded event manager logs.";
    dn-events-extensions:event-trigger-component-string "EEM";
    dn-events-extensions:event-group "Management";
    leaf policy-name {
      type string;
      description
        "The name of the policy.";
    }
    leaf user-name {
      type string;
      description
        "The user-name that is used by the policy.";
    }
  }

  notification EVENT_MANAGER_EVENT_POLICY_ADMIN_STATE_CONFIG {
    description
      "The user has changed Event-Manager event-policy admin-state configuration.";
    dn-events-extensions:event-severity-level "Info";
    dn-events-extensions:event-message-string "User {user-name} has changed event-policy {policy-name} admin-state configuration to {new-state}";
    dn-events-extensions:event-corrective-action-string "This is informational, no corrective action required.";
    dn-events-extensions:event-trigger-component-string "Transaction-manager";
    dn-events-extensions:event-group "Management";
    leaf user-name {
      type string;
      description
        "System user-name.";
    }
    leaf policy-name {
      type string;
      description
        "The name of the policy.";
    }
    leaf new-state {
      type string;
      description
        "The new admin state";
    }
  }

  notification EVENT_MANAGER_PERIODIC_POLICY_CONFIG_CHANGE_COMMITTED {
    description
      "Event manager triggered configuration change.";
    dn-events-extensions:event-severity-level "Info";
    dn-events-extensions:event-message-string "Configuration change successful: while executing periodic-policy {policy-name} with user {user-name} privileges.";
    dn-events-extensions:event-corrective-action-string "No corrective action.";
    dn-events-extensions:event-trigger-component-string "EEM";
    dn-events-extensions:event-group "Management";
    leaf policy-name {
      type string;
      description
        "The name of the policy.";
    }
    leaf user-name {
      type string;
      description
        "The user-name that is used by the policy.";
    }
  }

  notification EVENT_MANAGER_PERIODIC_POLICY_CONFIG_CHANGE_FAILED {
    description
      "Event manager failed to commit configuration change.";
    dn-events-extensions:event-severity-level "Error";
    dn-events-extensions:event-message-string "Configuration change failed: while executing periodic-policy {policy-name} with user {user-name} privileges.";
    dn-events-extensions:event-corrective-action-string "Check the embedded event manager logs.";
    dn-events-extensions:event-trigger-component-string "EEM";
    dn-events-extensions:event-group "Management";
    leaf policy-name {
      type string;
      description
        "The name of the policy.";
    }
    leaf user-name {
      type string;
      description
        "The user-name that is used by the policy.";
    }
  }

  notification EVENT_MANAGER_PERIODIC_POLICY_ADMIN_STATE_CONFIG {
    description
      "The user has changed Event-Manager periodic-policy admin-state configuration.";
    dn-events-extensions:event-severity-level "Info";
    dn-events-extensions:event-message-string "User {user-name} has changed periodic-policy {policy-name} admin-state configuration to {new-state}";
    dn-events-extensions:event-corrective-action-string "This is informational, no corrective action required.";
    dn-events-extensions:event-trigger-component-string "Transaction-manager";
    dn-events-extensions:event-group "Management";
    leaf user-name {
      type string;
      description
        "System user-name.";
    }
    leaf policy-name {
      type string;
      description
        "The name of the policy.";
    }
    leaf new-state {
      type string;
      description
        "The new admin state";
    }
  }

  notification EVENT_MANAGER_GENERIC_POLICY_CONFIG_CHANGE_COMMITTED {
    description
      "Event manager triggered configuration change.";
    dn-events-extensions:event-severity-level "Info";
    dn-events-extensions:event-message-string "Configuration change successful: while executing generic-policy {policy-name} with user {user-name} privileges.";
    dn-events-extensions:event-corrective-action-string "No corrective action.";
    dn-events-extensions:event-trigger-component-string "EEM";
    dn-events-extensions:event-group "Management";
    leaf policy-name {
      type string;
      description
        "The name of the policy.";
    }
    leaf user-name {
      type string;
      description
        "The user-name that is used by the policy.";
    }
  }

  notification EVENT_MANAGER_GENERIC_POLICY_CONFIG_CHANGE_FAILED {
    description
      "Event manager failed to commit configuration change.";
    dn-events-extensions:event-severity-level "Error";
    dn-events-extensions:event-message-string "Configuration change failed: while executing generic-policy {policy-name} with user {user-name} privileges.";
    dn-events-extensions:event-corrective-action-string "Check the embedded event manager logs.";
    dn-events-extensions:event-trigger-component-string "EEM";
    dn-events-extensions:event-group "Management";
    leaf policy-name {
      type string;
      description
        "The name of the policy.";
    }
    leaf user-name {
      type string;
      description
        "The user-name that is used by the policy.";
    }
  }

  notification EVENT_MANAGER_GENERIC_POLICY_ADMIN_STATE_CONFIG {
    description
      "The user has changed Event-Manager generic-policy admin-state configuration.";
    dn-events-extensions:event-severity-level "Info";
    dn-events-extensions:event-message-string "User {user-name} has changed generic-policy {policy-name} admin-state configuration to {new-state}.";
    dn-events-extensions:event-corrective-action-string "This is informational, no corrective action required.";
    dn-events-extensions:event-trigger-component-string "Transaction-manager";
    dn-events-extensions:event-group "Management";
    leaf user-name {
      type string;
      description
        "System user-name.";
    }
    leaf policy-name {
      type string;
      description
        "The name of the policy.";
    }
    leaf new-state {
      type string;
      description
        "The new admin state";
    }
  }

  notification EVENT_MANAGER_EVENT_POLICY_TERMINATED {
    description
      "Event manager stopped event-policy execution.";
    dn-events-extensions:event-severity-level "Warning";
    dn-events-extensions:event-message-string "event-manager terminated the execution of event-policy {policy-name} which matched system event {event-name} with attribute {attribute-name}, termination reason: {reason}.";
    dn-events-extensions:event-corrective-action-string "Check the reason field for more details.";
    dn-events-extensions:event-trigger-component-string "EEM";
    dn-events-extensions:event-group "Management";
    leaf policy-name {
      type string;
      description
        "The name of the policy.";
    }
    leaf event-name {
      type string;
      description
        "The system event that triggers the policy.";
    }
    leaf attribute-name {
      type string;
      description
        "The attribute name that the script receives.";
    }
    leaf reason {
      type string;
      description
        "Reason for the script termination
         (e.g. script max-runtime exceeded, user request command, configuration change, other)";
    }
  }

  notification EVENT_MANAGER_PERIODIC_POLICY_TERMINATED {
    description
      "Event manager stopped periodic-policy execution.";
    dn-events-extensions:event-severity-level "Warning";
    dn-events-extensions:event-message-string "event-manager terminated the execution of periodic-policy {policy-name}, termination reason: {reason}.";
    dn-events-extensions:event-corrective-action-string "Check the reason field for more details.";
    dn-events-extensions:event-trigger-component-string "EEM";
    dn-events-extensions:event-group "Management";
    leaf policy-name {
      type string;
      description
        "The name of the policy.";
    }
    leaf reason {
      type string;
      description
        "Reason for the script termination
         (e.g. script max-runtime exceeded, user request command, configuration change, other)";
    }
  }

  notification EVENT_MANAGER_GENERIC_POLICY_TERMINATED {
    description
      "Event manager stopped generic-policy execution.";
    dn-events-extensions:event-severity-level "Warning";
    dn-events-extensions:event-message-string "event-manager terminated the execution of generic-policy {policy-name}, termination reason: {reason}.";
    dn-events-extensions:event-corrective-action-string "Check the reason field for more details.";
    dn-events-extensions:event-trigger-component-string "EEM";
    dn-events-extensions:event-group "Management";
    leaf policy-name {
      type string;
      description
        "The name of the policy.";
    }
    leaf reason {
      type string;
      description
        "Reason for the script termination
         (e.g. user request command, configuration change, other)";
    }
  }

  notification EVENT_MANAGER_POLICY_INACTIVE {
    description
      "The following policy inactive.";
    dn-events-extensions:event-severity-level "Notice";
    dn-events-extensions:event-message-string "policy {policy-name} of type {policy-type} switched to inactive, reason {reason}.";
    dn-events-extensions:event-corrective-action-string "Check the reason field, for the termination reason.";
    dn-events-extensions:event-trigger-component-string "EEM";
    dn-events-extensions:event-group "Management";
    leaf policy-name {
      type string;
      description
        "The name of the policy.";
    }
    leaf policy-type {
      type string;
      description
        "The type of the policy.";
    }
    leaf reason {
      type string;
      description
        "The reason why policy inactive
         (e.g. policy finished execution, configuration change, misconfiguration, other)";
    }
  }

  notification EVENT_MANAGER_POLICY_ACTIVE {
    description
      "The following policy active.";
    dn-events-extensions:event-severity-level "Info";
    dn-events-extensions:event-message-string "policy {policy-name} of type {policy-type} switched to active.";
    dn-events-extensions:event-corrective-action-string "This is informational, no corrective action required.";
    dn-events-extensions:event-trigger-component-string "EEM";
    dn-events-extensions:event-group "Management";
    leaf policy-name {
      type string;
      description
        "The name of the policy.";
    }
    leaf policy-type {
      type string;
      description
        "The type of the policy.";
    }
  }

  notification EVENT_MANAGER_POLICY_TRIGGER_FAILED {
    description
      "The following policy failed to be triggered.";
    dn-events-extensions:event-severity-level "Error";
    dn-events-extensions:event-message-string "policy {policy-name} of type {policy-type} failed to be launched, reason {reason}.";
    dn-events-extensions:event-corrective-action-string "This is informational, no corrective action required.";
    dn-events-extensions:event-trigger-component-string "EEM";
    dn-events-extensions:event-group "Management";
    leaf policy-name {
      type string;
      description
        "The name of the policy.";
    }
    leaf policy-type {
      type string;
      description
        "The type of the policy.";
    }
    leaf reason {
      type string;
      description
        "The reason why policy inactive
         (e.g. policy infrastructure not ready, memory limit reached, other)";
    }
  }

  notification EVENT_MANAGER_POLICY_FINISHED {
    description
      "The following policy finished execution.";
    dn-events-extensions:event-severity-level "Info";
    dn-events-extensions:event-message-string "Policy {policy-name} of type {policy-type} finished execution.";
    dn-events-extensions:event-corrective-action-string "This is informational, no corrective action required.";
    dn-events-extensions:event-trigger-component-string "EEM";
    dn-events-extensions:event-group "Management";
    leaf policy-name {
      type string;
      description
        "The name of the policy.";
    }
    leaf policy-type {
      type string;
      description
        "The type of the policy.";
    }
  }

  // Console events

  notification CONSOLE_SESSION_LOGIN {
    description
      "The user has logged into the system via the console port.";
    dn-events-extensions:event-severity-level "Info";
    dn-events-extensions:event-message-string "User {user-name} has logged in to the system using console";
    dn-events-extensions:event-corrective-action-string "This is informational, no corrective action required.";
    dn-events-extensions:event-trigger-component-string "CLI";
    dn-events-extensions:event-group "Management";
    leaf user-name {
      type string;
      description
        "System user-name";
    }
  }

  notification CONSOLE_SESSION_LOGIN_FAILED {
    description
      "The user login attempt to system via the console was rejected due to incorrect credentials.";
    dn-events-extensions:event-severity-level "Warning";
    dn-events-extensions:event-message-string "User {user-name} login attempt to system console has been rejected due to incorrect credentials";
    dn-events-extensions:event-corrective-action-string "This is informational, no corrective action required.";
    dn-events-extensions:event-trigger-component-string "TBD";
    dn-events-extensions:event-group "Management";
    leaf user-name {
      type string;
      description
        "System user-name";
    }
  }

  notification CONSOLE_NODE_LOGIN {
    description
      "The user has logged into the node host OS prompt via the console port.";
    dn-events-extensions:event-severity-level "Info";
    dn-events-extensions:event-message-string "User {user-name} has logged in to the host OS prompt of the {node-type}-{node-id}";
    dn-events-extensions:event-corrective-action-string "This is informational, no corrective action required.";
    dn-events-extensions:event-trigger-component-string "";
    dn-events-extensions:event-group "Management";
    leaf user-name {
      type string;
      description
        "System user-name";
    }
    leaf node-type {
      type string;
      description
        "Node-type (NCC/NCP/NCF)";
    }
    leaf node-id {
      type string;
      description
        "Node ID (0-191)";
    }
  }

  notification CONSOLE_NODE_LOGIN_FAILED {
    description
      "The user login attempt to the console of the node was rejected due to incorrect credentials.";
    dn-events-extensions:event-severity-level "Warning";
    dn-events-extensions:event-message-string "User {user-name} login attempt to {node-type}-{node-id} console has been rejected due to incorrect credentials";
    dn-events-extensions:event-corrective-action-string "This is informational, no corrective action required.";
    dn-events-extensions:event-trigger-component-string "TBD";
    dn-events-extensions:event-group "Management";
    leaf user-name {
      type string;
      description
        "System user-name";
    }
    leaf node-type {
      type string;
      description
        "Node-type (NCC/NCP/NCF)";
    }
    leaf node-id {
      type string;
      description
        "Node ID (0-191)";
    }
  }

  // Flowspec events

  notification BGP_FLOWSPEC_UNSUPPORTED_RULE {
    description
      "Indication that a given flowspec rule cannot be installed";
    dn-events-extensions:event-severity-level "Warning";
    dn-events-extensions:event-message-string "BGP flowspec {address-family} rule cannot be applied due to {reason}. Rule NLRI: {nlri}, Actions: {actions}";
    dn-events-extensions:event-corrective-action-string "Verify rule attributes and overall flowspec scale";
    dn-events-extensions:event-trigger-component-string "WB";
    dn-events-extensions:event-group "BGP";
    leaf address-family {
      type string;
      description
        "flowspec address family, either ipv4 or ipv6";
    }
    leaf reason {
      type string;
      description
        "reason rule cannot be supported";
    }
    leaf nlri {
      type string;
      description
        "full flowspec rule nlri";
    }
    leaf actions {
      type string;
      description
        "string of flowspec rule action communities, can have more than a single action";
    }
  }

  // Flowspec Local events

  notification FLOWSPEC_LOCAL_UNSUPPORTED_RULE {
    description
      "Indication that a given flowspec local rule cannot be installed";
    dn-events-extensions:event-severity-level "Warning";
    dn-events-extensions:event-message-string "Flowspec Local {address-family} rule cannot be applied due to {reason}. Rule NLRI: {nlri}, Actions: {actions}";
    dn-events-extensions:event-corrective-action-string "Verify rule attributes and overall flowspec scale";
    dn-events-extensions:event-trigger-component-string "WB";
    dn-events-extensions:event-group "System";
    leaf address-family {
      type string;
      description
        "flowspec local address family, either ipv4 or ipv6";
    }
    leaf reason {
      type string;
      description
        "reason rule cannot be supported";
    }
    leaf nlri {
      type string;
      description
        "full flowspec rule nlri";
    }
    leaf actions {
      type string;
      description
        "string of flowspec local rule action communities, can have more than a single action";
    }
  }

  // BGP redistribute connected and imported to vrf events

  notification BGP_REDISTRIBUTE_CONNECTED_AND_IMPORT_TO_VRF_ROUTE_NOT_INSTALLED {
    description
      "A BGP route learned from an Access Connection interface cannot be redistributed  and imported into a VRF due to a lack of resources.";
    dn-events-extensions:event-severity-level "Warning";
    dn-events-extensions:event-message-string "Route(s) cannot be redistributed and imported into VRF {vrf-name} in ncp {ncp-id} due to lack of resources.";
    dn-events-extensions:event-corrective-action-string "Verify that the BGP redistribute connected rules and VRFs are correct.";
    dn-events-extensions:event-trigger-component-string "WB";
    dn-events-extensions:event-group "System";
    leaf vrf-name {
      type string;
      description
        "Name of the VRF";
    }
    leaf ncp-id {
      type uint16;
      description
        "NCP ID";
    }
  }

  notification BGP_REDISTRIBUTE_CONNECTED_AND_IMPORT_TO_VRF_ROUTE_NOT_INSTALLED_CLEARED {
    description
      "The routes that BGP learns from Access Connection interfaces and redistributes to the listed VRF can now be installed as resources have been freed.";
    dn-events-extensions:event-severity-level "Info";
    dn-events-extensions:event-message-string "Resources freed - Route(s) can be redistributed and imported into VRF {vrf-name} in ncp {ncp-id}.";
    dn-events-extensions:event-corrective-action-string "This is informational, no corrective action required.";
    dn-events-extensions:event-trigger-component-string "WB";
    dn-events-extensions:event-group "System";
    leaf vrf-name {
      type string;
      description
        "Name of the VRF";
    }
    leaf ncp-id {
      type uint16;
      description
        "NCP ID";
    }
  }

  // ospf notifications

  notification OSPF_NEIGHBOR_STATE_CHANGE {
    description
      "The OSPF neighbor adjacency state has changed.";
    dn-events-extensions:event-severity-level "Info";
    dn-events-extensions:event-message-string "OSPF instance {instance} router {router-id} adjacency status with neighbor {neighbor-address} on interface {if-name} changed to {neighbor-state}";
    dn-events-extensions:event-corrective-action-string "This is informational, no corrective action required.";
    dn-events-extensions:event-trigger-component-string "ospf";
    dn-events-extensions:event-group "OSPF";
    dn-events-extensions:event-snmp-trap-name "ospfNbrStateChange";
    dn-events-extensions:event-snmp-trap-oid ".1.3.6.1.2.1.14.16.2.2";
    dn-events-extensions:event-snmp-trap-vars "ospfRouterId.0 {router-id} ; ospfNbrIpAddr.0 {neighbor-address} ; ospfNbrAddressLessIndex.0 {if-index} ; ospfNbrRtrId.0 {neighbor-router-id} ; ospfNbrState.0 {neighbor-state}";
    leaf instance {
      type string;
      description
        "OSPF instance name";
    }
    leaf router-id {
      type string;
      description
        "OSPF Router ID";
    }
    leaf neighbor-address {
      type string;
      description
        "Neighbor peer IP address";
    }
    leaf if-name {
      type string;
      description
        "Interface name";
    }
    leaf if-index {
      type uint32 {
        range "1..2147483647";
      }
      description
        "The identifier of this interface relevant to this notification";
    }
    leaf neighbor-router-id {
      type string;
      description
        "The OSPF neighbor Router ID";
    }
    leaf neighbor-state {
      type enumeration {
        enum down {
          value 1;
        }
        enum attempt {
          value 2;
        }
        enum init {
          value 3;
        }
        enum twoway {
          value 4;
        }
        enum exchangestart {
          value 5;
        }
        enum exchange {
          value 6;
        }
        enum loading {
          value 7;
        }
        enum full {
          value 8;
        }
      }
      description
        "The current state of the OSPF neighbor adjacency.";
    }
  }

  notification OSPF_INTERFACE_STATE_CHANGE {
    description
      "The OSPF intrerface state has changed.";
    dn-events-extensions:event-severity-level "Info";
    dn-events-extensions:event-message-string "OSPF instance {instance} interface {if-name} status changed to {ospf-if-state}";
    dn-events-extensions:event-corrective-action-string "This is informational, no corrective action required.";
    dn-events-extensions:event-trigger-component-string "ospf";
    dn-events-extensions:event-group "OSPF";
    dn-events-extensions:event-snmp-trap-name "ospfIfStateChange";
    dn-events-extensions:event-snmp-trap-oid ".1.3.6.1.2.1.14.16.2.16";
    dn-events-extensions:event-snmp-trap-vars "ospfRouterId.0 {router-id} ; ospfIfIpAddress.0 {if-ip-address} ; ospfAddressLessIf.0 {if-index} ; ospfIfState.0 {ospf-if-state}";
    leaf instance {
      type string;
      description
        "OSPF instance name";
    }
    leaf router-id {
      type string;
      description
        "OSPF Router ID";
    }
    leaf if-ip-address {
      type string;
      description
        "OSPF Interface IP address";
    }
    leaf if-name {
      type string;
      description
        "OSPF Interface name";
    }
    leaf if-index {
      type uint32 {
        range "1..2147483647";
      }
      description
        "The identifier of this interface relevant to this notification";
    }
    leaf ospf-if-state {
      type enumeration {
        enum down {
          value 1;
        }
        enum loopback {
          value 2;
        }
        enum waiting {
          value 3;
        }
        enum point-to-point {
          value 4;
        }
        enum designated-router {
          value 5;
        }
        enum backup-designated-router {
          value 6;
        }
        enum other-designated-router {
          value 7;
        }
      }
      description
        "The current state of the OSPF interface.";
    }
  }

  notification OSPF_AUTHENTICATION_FAILED {
    description
      "OSPF failed to validate a received OSPF packet, either due to key mismatch or an authentication type conflict. The packet was dropped.";
    dn-events-extensions:event-severity-level "Warning";
    dn-events-extensions:event-message-string "OSPF instance {instance} received {ospf-packet-type} packet on interface {interface-name} from source {packet-src}. {ospf-packet-type} authentication failed due to {auth-failure-type}. Packet was dropped.";
    dn-events-extensions:event-corrective-action-string "Check that the password configuration is the same on both the local and remote system.";
    dn-events-extensions:event-trigger-component-string "OSPF";
    dn-events-extensions:event-group "OSPF";
    dn-events-extensions:event-snmp-trap-name "ospfIfAuthFailure";
    dn-events-extensions:event-snmp-trap-oid "1.3.6.1.2.1.14.16.2.6";
    dn-events-extensions:event-snmp-trap-vars "ospfRouterId.0 {router-id} ; ospfIfIpAddress.0 {ospf-if-address} ; ospfAddressLessIf.0 {ospf-address-less-if} ; ospfPacketSrc.0 {packet-src} ; ospfConfigErrorType.0 {auth-failure-type} ; ospfPacketType.0 {ospf-packet-type}";
    leaf router-id {
      type string;
      description
        "The originator of the trap";
    }
    leaf instance {
      type string;
      description
        "OSPF instance name";
    }
    leaf ospf-packet-type {
      type enumeration {
        enum hello {
          value 1;
        }
        enum dbDescript {
          value 2;
        }
        enum lsReq {
          value 3;
        }
        enum lsUpdate {
          value 4;
        }
        enum lsAck {
          value 5;
        }
        enum nullPacket {
          value 6;
        }
      }
      description
        "OSPF packet type";
    }
    leaf interface-name {
      type string;
      description
        "local interface name";
    }
    leaf ospf-if-address {
      type string;
      description
        "The local ip address of this OSPF interface.";
    }
    leaf ospf-address-less-if {
      type uint32;
      description
        "For the purpose of easing the instancing of
         addressed and addressless interfaces; this
         variable takes the value 0 on interfaces with
         IP addresses and the corresponding value of
         ifIndex for interfaces having no IP address.";
    }
    leaf packet-src {
      description
        "The IP address of an inbound packet that cannot
         be identified by a neighbor instance";
      type string;
    }
    leaf auth-failure-type {
      type enumeration {
        enum authTypeMismatch {
          value 5;
        }
        enum authFailure {
          value 6;
        }
      }
      description
        "Potential types of authentication conflicts.";
    }
  }

  notification OSPF_MAX_AGE_LSA {
    description
      "One of the  link-state advertisements (LSA) in the router's link state database has aged to MaxAge.";
    dn-events-extensions:event-severity-level "Notice";
    dn-events-extensions:event-message-string "OSPF instance {instance} LS type {ls-type} with ID {ls-id} received from area {area-id} with Router-ID {org-router-id} has aged to MaxAge";
    dn-events-extensions:event-corrective-action-string "Check that originating router is operational.";
    dn-events-extensions:event-trigger-component-string "OSPF";
    dn-events-extensions:event-group "OSPF";
    dn-events-extensions:event-snmp-trap-name "ospfMaxAgeLsa";
    dn-events-extensions:event-snmp-trap-oid "1.3.6.1.2.1.14.16.2.13";
    dn-events-extensions:event-snmp-trap-vars "ospfRouterId.0 {router-id} ; ospfLsdbAreaId.0 {area-id} ; ospfLsdbType.0 {ls-type} ; ospfLsdbLsid.0 {ls-id} ; ospfLsdbRouterId.0 {org-router-id}";
    leaf router-id {
      type string;
      description
        "The originator of the trap";
    }
    leaf instance {
      type string;
      description
        "OSPF instance name";
    }
    leaf ls-type {
      type enumeration {
        enum router-link {
          value 1;
        }
        enum network-link {
          value 2;
        }
        enum summary-link {
          value 3;
        }
        enum as-summary-link {
          value 4;
        }
        enum as-external-link {
          value 5;
        }
        enum multicast-link {
          value 6;
        }
        enum nssa-external-link {
          value 7;
        }
        enum area-opaque-link {
          value 10;
        }
      }
      description
        "The type of the link state advertisement.
         Each link state type has a separate advertisement
         format.
         Note: External link state advertisements are permitted
         for backward compatibility, but should be displayed
         in the ospfAsLsdbTable rather than here.";
    }
    leaf ls-id {
      type string;
      description
        "The Link State ID is an LS Type Specific field
         containing either a Router ID or an IP address;
         it identifies the piece of the routing domain
         that is being described by the advertisement.";
    }
    leaf area-id {
      type string;
      description
        "The 32-bit identifier of the area from which the LSA was received, 0.0.0.0 for AS Externals ";
    }
    leaf org-router-id {
      type string;
      description
        "The IP address that uniquely identifies the
         originating router in the Autonomous System.";
    }
  }

  notification OSPF_INVALID_RECEIVED_PACKET {
    description
      "A packet has been received on a non-virtual interface from a router whose configuration parameters conflict with this router's configuration parameters.";
    dn-events-extensions:event-severity-level "Notice";
    dn-events-extensions:event-message-string "OSPF instance {instance} received invalid {ospf-packet-type} packet on interface {interface-name} from source {packet-src}. Error type: {ospf-error-type}";
    dn-events-extensions:event-corrective-action-string "Check OSPF configuration on source system matches configuration on local system";
    dn-events-extensions:event-trigger-component-string "OSPF";
    dn-events-extensions:event-group "OSPF";
    dn-events-extensions:event-snmp-trap-name "ospfIfConfigError";
    dn-events-extensions:event-snmp-trap-oid "1.3.6.1.2.1.14.16.2.4";
    dn-events-extensions:event-snmp-trap-vars "ospfRouterId.0 {router-id} ; ospfIfIpAddress.0 {ospf-if-address} ; ospfAddressLessIf.0 {ospf-address-less-if} ; ospfPacketSrc.0 {packet-src} ; ospfConfigErrorType.0 {ospf-error-type} ; ospfPacketType.0 {ospf-packet-type}";
    leaf router-id {
      type string;
      description
        "The originator of the trap";
    }
    leaf instance {
      type string;
      description
        "OSPF instance name";
    }
    leaf ospf-packet-type {
      type enumeration {
        enum hello {
          value 1;
        }
        enum dbDescript {
          value 2;
        }
        enum lsReq {
          value 3;
        }
        enum lsUpdate {
          value 4;
        }
        enum lsAck {
          value 5;
        }
        enum nullPacket {
          value 6;
        }
      }
      description
        "OSPF packet type";
    }
    leaf interface-name {
      type string;
      description
        "local interface name";
    }
    leaf ospf-if-address {
      type string;
      description
        "The local ip address of this OSPF interface.";
    }
    leaf ospf-address-less-if {
      type uint32;
      description
        "For the purpose of easing the instancing of
         addressed and addressless interfaces; this
         variable takes the value 0 on interfaces with
         IP addresses and the corresponding value of
         ifIndex for interfaces having no IP address.";
    }
    leaf packet-src {
      description
        "The IP address of an inbound packet that cannot
         be identified by a neighbor instance";
      type string;
    }
    leaf ospf-error-type {
      type enumeration {
        enum badVersion {
          value 1;
        }
        enum areaMismatch {
          value 2;
        }
        enum unknownNbmaNbr {
          value 3;
        }
        enum unknownVirtualNbr {
          value 4;
        }
        enum authTypeMismatch {
          value 5;
        }
        enum authFailure {
          value 6;
        }
        enum netMaskMismatch {
          value 7;
        }
        enum helloIntervalMismatch {
          value 8;
        }
        enum deadIntervalMismatch {
          value 9;
        }
        enum optionMismatch {
          value 10;
        }
        enum mtuMismatch {
          value 11;
        }
        enum duplicateRouterId {
          value 12;
        }
        enum noError {
          value 13;
        }
      }
      description
        "Potential types of configuration conflicts.";
    }
  }

  notification OSPF_TX_RETRANSMIT {
    description
      "An OSPF packet has been retransmitted on a non-virtual interface. All packets that may be retransmitted are associated with an LSDB entry.";
    dn-events-extensions:event-severity-level "Debug";
    dn-events-extensions:event-message-string "OSPF instance {instance} retransmitted an {ospf-packet-type} packet on interface {interface-name} to neighbor {neighbor-router-id}. Update includes LSA type {ls-type} with ID {ls-id} of originating router {org-router-id}";
    dn-events-extensions:event-corrective-action-string "Check the egress interface congestion state.";
    dn-events-extensions:event-trigger-component-string "OSPF";
    dn-events-extensions:event-group "OSPF";
    dn-events-extensions:event-snmp-trap-name "ospfTxReTransmit";
    dn-events-extensions:event-snmp-trap-oid "1.3.6.1.2.1.14.16.2.10";
    dn-events-extensions:event-snmp-trap-vars "ospfRouterId.0 {router-id} ; ospfIfIpAddress.0 {ospf-if-address} ; ospfAddressLessIf.0 {ospf-address-less-if}; ospfNbrRtrId.0 {neighbor-router-id}; ospfPacketType.0 {ospf-packet-type} ; ospfLsdbType.0 {ls-type}; ospfLsdbLsid.0 {ls-id} ; ospfLsdbRouterId.0 {org-router-id}";
    leaf router-id {
      type string;
      description
        "The originator of the trap";
    }
    leaf instance {
      type string;
      description
        "OSPF instance name";
    }
    leaf ospf-packet-type {
      type enumeration {
        enum lsUpdate {
          value 4;
        }
      }
      description
        "OSPF packet type";
    }
    leaf interface-name {
      type string;
      description
        "local interface name";
    }
    leaf ospf-if-address {
      type string;
      description
        "The local ip address of this OSPF interface.";
    }
    leaf ospf-address-less-if {
      type uint32;
      description
        "For the purpose of easing the instancing of
         addressed and addressless interfaces; this
         variable takes the value 0 on interfaces with
         IP addresses and the corresponding value of
         ifIndex for interfaces having no IP address.";
    }
    leaf neighbor-router-id {
      type string;
      description
        "Neighbor router-id to whom LS update required to be sent";
    }
    leaf ls-type {
      type enumeration {
        enum router-link {
          value 1;
        }
        enum network-link {
          value 2;
        }
        enum summary-link {
          value 3;
        }
        enum as-summary-link {
          value 4;
        }
        enum as-external-link {
          value 5;
        }
        enum multicast-link {
          value 6;
        }
        enum nssa-external-link {
          value 7;
        }
        enum area-opaque-link {
          value 10;
        }
      }
      description
        "The type of the link state advertisement.
         Each link state type has a separate advertisement
         format.
         Note: External link state advertisements are permitted
         for backward compatibility, but should be displayed
         in the ospfAsLsdbTable rather than here.";
    }
    leaf ls-id {
      type string;
      description
        "The Link State ID is an LS Type Specific field
         containing either a Router ID or an IP address;
         it identifies the piece of the routing domain
         that is being described by the advertisement.";
    }
    leaf org-router-id {
      type string;
      description
        "The IP address that uniquely identifies the
         originating router in the Autonomous System.";
    }
  }

  notification OSPF_MAXIMUM_ADJACENCIES_LIMIT_REACHED {
    description
      "The number of OSPF adjacencies has reached the configured system limit.";
    dn-events-extensions:event-severity-level "Warning";
    dn-events-extensions:event-message-string "Number of OSPF adjacencies has reached system limit of {limit}";
    dn-events-extensions:event-corrective-action-string "No corrective action.";
    dn-events-extensions:event-trigger-component-string "ospf";
    dn-events-extensions:event-group "OSPF";
    leaf limit {
      type uint16;
      description
        "The accumulated OSPF adjacencies scale.";
    }
  }

  notification OSPF_MAXIMUM_ADJACENCIES_LIMIT_CLEARED {
    description
      "OSPF adjacencies have been removed, the number of OSPF adjacencies is below the system limit.";
    dn-events-extensions:event-severity-level "Info";
    dn-events-extensions:event-message-string "Number of OSPF adjacencies is below the system limit of {limit}";
    dn-events-extensions:event-corrective-action-string "This is informational, no corrective action required.";
    dn-events-extensions:event-trigger-component-string "ospf";
    dn-events-extensions:event-group "OSPF";
    leaf limit {
      type uint16;
      description
        "The accumulated OSPF adjacencies scale.";
    }
  }

  notification OSPF_MAXIMUM_ADJACENCIES_THRESHOLD_EXCEEDED {
    description
      "The number of OSPF adjacencies has crossed the system threshold.";
    dn-events-extensions:event-severity-level "Notice";
    dn-events-extensions:event-message-string "Number of OSPF adjacencies has crossed the system threshold {threshold}% limit of {limit}, the number of OSPF adjacencies are ({numeric-value})";
    dn-events-extensions:event-corrective-action-string "No corrective action.";
    dn-events-extensions:event-trigger-component-string "ospf";
    dn-events-extensions:event-group "OSPF";
    leaf threshold {
      type uint8;
      description
        "Threshold percent";
    }
    leaf numeric-value {
      type uint16;
      description
        "Current number of OSPF adjacencies";
    }
    leaf limit {
      type uint16;
      description
        "The accumulated OSPF adjacencies scale";
    }
  }

  notification OSPF_MAXIMUM_ADJACENCIES_THRESHOLD_CLEARED {
    description
      "The number of OSPF adjacencies is below the system threshold.";
    dn-events-extensions:event-severity-level "Info";
    dn-events-extensions:event-message-string "Number of OSPF adjacencies is below the system threshold {threshold}% of the limit ({limit}), the current number of OSPF adjacencies are ({numeric-value})";
    dn-events-extensions:event-corrective-action-string "This is informational, no corrective action required.";
    dn-events-extensions:event-trigger-component-string "ospf";
    dn-events-extensions:event-group "OSPF";
    leaf threshold {
      type uint8;
      description
        "Threshold percent";
    }
    leaf numeric-value {
      type uint16;
      description
        "Current number of OSPF adjacencies";
    }
    leaf limit {
      type uint16;
      description
        "The accumulated OSPF adjacencies scale.";
    }
  }

  notification OSPF_MAXIMUM_ROUTES_LIMIT_REACHED {
    description
      "The number of OSPF routes has reached the system limit.";
    dn-events-extensions:event-severity-level "Warning";
    dn-events-extensions:event-message-string "Number of OSPF routes has reached the system limit of {limit} routes";
    dn-events-extensions:event-corrective-action-string "No corrective action.";
    dn-events-extensions:event-trigger-component-string "ospf";
    dn-events-extensions:event-group "OSPF";
    leaf limit {
      type uint16;
      description
        "The accumulated OSPF routes scale on all address-families";
    }
  }

  notification OSPF_MAXIMUM_ROUTES_LIMIT_CLEARED {
    description
      "Routes have been removed, the number of OSPF routes is below the system limit.";
    dn-events-extensions:event-severity-level "Info";
    dn-events-extensions:event-message-string "Number of OSPF routes is below the system limit of {limit} routes";
    dn-events-extensions:event-corrective-action-string "This is informational, no corrective action required.";
    dn-events-extensions:event-trigger-component-string "ospf";
    dn-events-extensions:event-group "OSPF";
    leaf limit {
      type uint16;
      description
        "The accumulated OSPF routes scale on all address-families";
    }
  }

  notification OSPF_MAXIMUM_ROUTES_THRESHOLD_EXCEEDED {
    description
      "The number of OSPF routes has crossed the system threshold.";
    dn-events-extensions:event-severity-level "Notice";
    dn-events-extensions:event-message-string "Number of OSPF routes has crossed the system threshold {threshold}% of the limit ({limit}), the current number of routes are ({numeric-value})";
    dn-events-extensions:event-corrective-action-string "No corrective action.";
    dn-events-extensions:event-trigger-component-string "ospf";
    dn-events-extensions:event-group "OSPF";
    leaf threshold {
      type uint8;
      description
        "Threshold percent";
    }
    leaf numeric-value {
      type uint16;
      description
        "Current number of OSPF routes";
    }
    leaf limit {
      type uint16;
      description
        "The accumulated OSPF routes scale on all address-families";
    }
  }

  notification OSPF_MAXIMUM_ROUTES_THRESHOLD_CLEARED {
    description
      "The number of OSPF routes is below the system threshold.";
    dn-events-extensions:event-severity-level "Info";
    dn-events-extensions:event-message-string "Number of OSPF routes is below the system threshold {threshold}% of the limit ({limit}), the current number of routes are ({numeric-value})";
    dn-events-extensions:event-corrective-action-string "This is informational, no corrective action required.";
    dn-events-extensions:event-trigger-component-string "ospf";
    dn-events-extensions:event-group "OSPF";
    leaf threshold {
      type uint8;
      description
        "Threshold percent";
    }
    leaf numeric-value {
      type uint16;
      description
        "Current number of OSPF routes";
    }
    leaf limit {
      type uint16;
      description
        "The accumulated OSPF routes scale on all address-families";
    }
  }

  notification OSPF_MAXIMUM_REDISTRIBUTED_PREFIXES_LIMIT_REACHED {
    description
      "The number of OSPF redistributed prefixes has reached the system limit.";
    dn-events-extensions:event-severity-level "Warning";
    dn-events-extensions:event-message-string "OSPF instance {instance}: Number of OSPF redistributed prefixes has reached the system limit of {limit}";
    dn-events-extensions:event-corrective-action-string "No corrective action.";
    dn-events-extensions:event-trigger-component-string "ospf";
    dn-events-extensions:event-group "OSPF";
    leaf instance {
      type string;
      description
        "OSPF instance name";
    }
    leaf limit {
      type uint16;
      description
        "The accumulated OSPF redistributed prefixes scale on all address-families";
    }
  }

  notification OSPF_MAXIMUM_REDISTRIBUTED_PREFIXES_LIMIT_CLEARED {
    description
      "redistributed prefixes have been reduced, the number of OSPF redistributed prefixes is below the system limit.";
    dn-events-extensions:event-severity-level "Info";
    dn-events-extensions:event-message-string "OSPF instance {instance}: Number of OSPF redistributed prefixes is below the system limit of {limit}";
    dn-events-extensions:event-corrective-action-string "This is informational, no corrective action required.";
    dn-events-extensions:event-trigger-component-string "ospf";
    dn-events-extensions:event-group "OSPF";
    leaf instance {
      type string;
      description
        "OSPF instance name";
    }
    leaf limit {
      type uint16;
      description
        "The accumulated OSPF redistributed prefixes scale on all address-families";
    }
  }

  notification OSPF_MAXIMUM_REDISTRIBUTED_PREFIXES_THRESHOLD_EXCEEDED {
    description
      "The number of OSPF redistributed prefixes has crossed the system threshold.";
    dn-events-extensions:event-severity-level "Notice";
    dn-events-extensions:event-message-string "OSPF instance {instance}: Number of OSPF redistributed prefixes has crossed the system threshold {threshold}% of the limit ({limit}), the current number of redistributed prefixes are ({numeric-value})";
    dn-events-extensions:event-corrective-action-string "No corrective action.";
    dn-events-extensions:event-trigger-component-string "ospf";
    dn-events-extensions:event-group "OSPF";
    leaf instance {
      type string;
      description
        "OSPF instance name";
    }
    leaf threshold {
      type uint8;
      description
        "Threshold percent";
    }
    leaf numeric-value {
      type uint16;
      description
        "Current number of OSPF redistributed prefixes";
    }
    leaf limit {
      type uint16;
      description
        "The accumulated OSPF redistributed prefixes scale on all address-families";
    }
  }

  notification OSPF_MAXIMUM_REDISTRIBUTED_PREFIXES_THRESHOLD_CLEARED {
    description
      "The number of OSPF redistributed prefixes is below the system threshold.";
    dn-events-extensions:event-severity-level "Info";
    dn-events-extensions:event-message-string "OSPF instance {instance}: Number of OSPF redistributed prefixes is below the system threshold {threshold}% of the limit ({limit}), the current number of redistributed prefixes are ({numeric-value})";
    dn-events-extensions:event-corrective-action-string "This is informational, no corrective action required.";
    dn-events-extensions:event-trigger-component-string "ospf";
    dn-events-extensions:event-group "OSPF";
    leaf instance {
      type string;
      description
        "OSPF instance name";
    }
    leaf threshold {
      type uint8;
      description
        "Threshold percent";
    }
    leaf numeric-value {
      type uint16;
      description
        "Current number of OSPF redistributed prefixes";
    }
    leaf limit {
      type uint16;
      description
        "The accumulated OSPF redistributed prefixes scale on all address-families";
    }
  }

  notification OSPF_GRACEFUL_RESTART_STATUS_CHANGE {
    description
      "The OSPF Graceful Restart state has changed.";
    dn-events-extensions:event-severity-level "Info";
    dn-events-extensions:event-message-string "OSPF router {router-id} process restarted. Graceful Restart state {gr-state} {gr-sub-state}. Graceful Restart grace period {grace-period} seconds";
    dn-events-extensions:event-corrective-action-string "This is informational, no corrective action required.";
    dn-events-extensions:event-trigger-component-string "ospf";
    dn-events-extensions:event-group "OSPF";
    dn-events-extensions:event-snmp-trap-name "ospfRestartStatusChange";
    dn-events-extensions:event-snmp-trap-oid ".1.3.6.1.2.1.14.16.2.18";
    dn-events-extensions:event-snmp-trap-vars
      "ospfRouterId.0 {router-id} ; ospfRestartStatus.0 {gr-state} ;
       ospfRestartInterval.0 {grace-period} ; ospfRestartExitReason.0 {gr-sub-state}";
    leaf router-id {
      type string;
      description
        "OSPF Router ID";
    }
    leaf gr-state {
      type enumeration {
        enum not-restarting {
          value 1;
        }
        enum planned-restart {
          value 2;
        }
        enum unplanned-restart {
          value 3;
        }
      }
      description
        "Current status of OSPF graceful restart.";
    }
    leaf grace-period {
      type uint16 {
        range "60..1800";
      }
      description
        "Configured OSPF graceful restart timeout interval.";
    }
    leaf gr-sub-state {
      type enumeration {
        enum none {
          value 1;
        }
        enum in-progress {
          value 2;
        }
        enum completed {
          value 3;
        }
        enum time-out {
          value 4;
        }
        enum topology-changed {
          value 5;
        }
      }
      description
        "Describes the outcome of the last attempt at a
         graceful restart.  If the value is 'none', no restart
         has yet been attempted.  If the value is 'inProgress',
         a restart attempt is currently underway.";
    }
  }

  notification OSPF_NEIGHBOR_GRACEFUL_RESTART_HELPER_STATUS_CHANGE {
    description
      "The Graceful Restart Helper state for an OSPF neighbor has changed.";
    dn-events-extensions:event-severity-level "Info";
    dn-events-extensions:event-message-string "OSPF router {router-id} neighbor {neighbor-router-id} on interface {if-name} restarted. Neighbor address {neighbor-address}. Graceful Restart Helper state {gr-helper-state} {gr-helper-sub-state}. Graceful Restart timeout {gr-interval-timeout} seconds";
    dn-events-extensions:event-corrective-action-string "This is informational, no corrective action required.";
    dn-events-extensions:event-trigger-component-string "ospf";
    dn-events-extensions:event-group "OSPF";
    dn-events-extensions:event-snmp-trap-name "ospfNbrRestartHelperStatusChange";
    dn-events-extensions:event-snmp-trap-oid ".1.3.6.1.2.1.14.16.2.19";
    dn-events-extensions:event-snmp-trap-vars
      "ospfRouterId.0 {router-id} ; ospfNbrIpAddr.0 {neighbor-address} ;
       ospfNbrAddressLessIndex.0 {if-index} ; ospfNbrRtrId.0 {neighbor-router-id} ;
       ospfNbrRestartHelperStatus.0 {gr-helper-state} ; ospfNbrRestartHelperAge.0 {gr-interval-timeout} ;
       ospfNbrRestartHelperExitReason.0 {gr-helper-sub-state}";
    leaf router-id {
      type string;
      description
        "OSPF Router ID";
    }
    leaf neighbor-address {
      type string;
      description
        "Neighbor peer IP address";
    }
    leaf if-name {
      type string;
      description
        "Interface name";
    }
    leaf if-index {
      type uint32 {
        range "1..2147483647";
      }
      description
        "The identifier of this interface relevant to this notification";
    }
    leaf neighbor-router-id {
      type string;
      description
        "The OSPF neighbor Router ID";
    }
    leaf gr-helper-state {
      type enumeration {
        enum not-helping {
          value 1;
        }
        enum helping {
          value 2;
        }
      }
      description
        "Indicates whether the router is acting
         as a graceful restart helper for the neighbor.";
    }
    leaf gr-interval-timeout {
      type uint32;
      description
        "Remaining time (in seconds) in current OSPF graceful restart
         interval, if the router is acting as a restart
         helper for the neighbor.";
    }
    leaf gr-helper-sub-state {
      type enumeration {
        enum none {
          value 1;
        }
        enum in-progress {
          value 2;
        }
        enum completed {
          value 3;
        }
        enum time-out {
          value 4;
        }
        enum topology-changed {
          value 5;
        }
      }
      description
        "Describes the outcome of the last attempt at acting
         as a graceful restart helper for the neighbor.";
    }
  }

  notification OSPF_NSR_RECOVERED {
    description
      "The system performed an OSPF Non-Stop Routing recovery due to a restart of the ospfd process.";
    dn-events-extensions:event-severity-level "Notice";
    dn-events-extensions:event-message-string "OSPF Non-Stop Routing recovery was performed due to a restart of the ospfd process";
    dn-events-extensions:event-corrective-action-string "This is informational, no corrective action required.";
    dn-events-extensions:event-trigger-component-string "OSPF";
    dn-events-extensions:event-group "OSPF";
  }

  notification OSPF_NSR_RECOVERY_FAILED {
    description
      "The OSPF process failed to recover in Non-Stop Routing mode.";
    dn-events-extensions:event-severity-level "Warning";
    dn-events-extensions:event-message-string "Ospfd process failed to recover in Non-Stop Routing mode";
    dn-events-extensions:event-corrective-action-string "Verify NSR readiness prior to the failure event. If the database was synchronized prior to the failure event, contact Customer Support.";
    dn-events-extensions:event-trigger-component-string "OSPF";
    dn-events-extensions:event-group "OSPF";
  }

  notification OSPFv3_NEIGHBOR_STATE_CHANGE {
    description
      "The OSPF neighbor adjacency state has changed.";
    dn-events-extensions:event-severity-level "Info";
    dn-events-extensions:event-message-string "OSPFv3 router {router-id} adjacency status with neighbor {neighbor-address} on interface {if-name} changed to {neighbor-state}";
    dn-events-extensions:event-corrective-action-string "This is informational, no corrective action required.";
    dn-events-extensions:event-trigger-component-string "ospfv3";
    dn-events-extensions:event-group "OSPFv3";
    dn-events-extensions:event-snmp-trap-name "ospfv3NbrStateChange";
    dn-events-extensions:event-snmp-trap-oid ".1.3.6.1.2.1.191.0.2";
    dn-events-extensions:event-snmp-trap-vars "ospfv3RouterId.0 {router-id-for-trap} ; ospfv3NbrState.{neighbor-router-id} {neighbor-state}";
    leaf router-id {
      type string;
      description
        "OSPFv3 Router ID";
    }
    leaf router-id-for-trap {
      type uint32 {
        range "1..4294967295";
      }
      description
        "OSPFv3 Router ID";
    }
    leaf neighbor-address {
      type string;
      description
        "Neighbor peer IP address";
    }
    leaf if-name {
      type string;
      description
        "Interface name";
    }
    leaf neighbor-router-id {
      type uint32 {
        range "1..4294967295";
      }
      description
        "The OSPFv3 neighbor Router ID";
    }
    leaf neighbor-state {
      type enumeration {
        enum down {
          value 1;
        }
        enum attempt {
          value 2;
        }
        enum init {
          value 3;
        }
        enum twoway {
          value 4;
        }
        enum exchangestart {
          value 5;
        }
        enum exchange {
          value 6;
        }
        enum loading {
          value 7;
        }
        enum full {
          value 8;
        }
      }
      description
        "The current state of the OSPFv3 neighbor adjacency.";
    }
  }

  notification OSPFv3_INTERFACE_STATE_CHANGE {
    description
      "The OSPF intrerface state has changed.";
    dn-events-extensions:event-severity-level "Info";
    dn-events-extensions:event-message-string "OSPFv3 interface {if-name} status changed to {ospf-if-state}";
    dn-events-extensions:event-corrective-action-string "This is informational, no corrective action required.";
    dn-events-extensions:event-trigger-component-string "ospfv3";
    dn-events-extensions:event-group "OSPFv3";
    dn-events-extensions:event-snmp-trap-name "ospfv3IfStateChange";
    dn-events-extensions:event-snmp-trap-oid ".1.3.6.1.2.1.191.0.10";
    dn-events-extensions:event-snmp-trap-vars "ospfv3RouterId.0 {router-id} ; ospfv3IfState.{if-index} {ospf-if-state}";
    leaf router-id {
      type uint32 {
        range "1..4294967295";
      }
      description
        "OSPFv3 Router ID";
    }
    leaf if-name {
      type string;
      description
        "OSPFv3 Interface name";
    }
    leaf if-index {
      type uint32;
      description
        "SNMP Interface index";
    }
    leaf ospf-if-state {
      type enumeration {
        enum down {
          value 1;
        }
        enum loopback {
          value 2;
        }
        enum waiting {
          value 3;
        }
        enum point-to-point {
          value 4;
        }
        enum designated-router {
          value 5;
        }
        enum backup-designated-router {
          value 6;
        }
        enum other-designated-router {
          value 7;
        }
        enum standby {
          value 8;
        }
      }
      description
        "The current state of the OSPFv3 interface.";
    }
  }

  notification OSPFv3_MAXIMUM_REDISTRIBUTED_PREFIXES_LIMIT_REACHED {
    description
      "The number of OSPFv3 redistributed prefixes has reached the system limit.";
    dn-events-extensions:event-severity-level "Warning";
    dn-events-extensions:event-message-string "Number of OSPFv3 redistributed prefixes has reached the system limit of {limit}";
    dn-events-extensions:event-corrective-action-string "No corrective action.";
    dn-events-extensions:event-trigger-component-string "ospfv3";
    dn-events-extensions:event-group "OSPFv3";
    leaf limit {
      type uint16;
      description
        "The accumulated OSPFv3 redistributed prefixes scale on all address-families";
    }
  }

  notification OSPFv3_MAXIMUM_REDISTRIBUTED_PREFIXES_LIMIT_CLEARED {
    description
      "redistributed prefixes have been reduced, the number of OSPFv3 redistributed prefixes is below the system limit.";
    dn-events-extensions:event-severity-level "Info";
    dn-events-extensions:event-message-string "Number of OSPFv3 redistributed prefixes is below the system limit of {limit}";
    dn-events-extensions:event-corrective-action-string "This is informational, no corrective action required.";
    dn-events-extensions:event-trigger-component-string "ospfv3";
    dn-events-extensions:event-group "OSPFv3";
    leaf limit {
      type uint16;
      description
        "The accumulated OSPFv3 redistributed prefixes scale on all address-families";
    }
  }

  notification OSPFv3_MAXIMUM_REDISTRIBUTED_PREFIXES_THRESHOLD_EXCEEDED {
    description
      "The number of OSPFv3 redistributed prefixes has crossed the system threshold.";
    dn-events-extensions:event-severity-level "Notice";
    dn-events-extensions:event-message-string "Number of OSPFv3 redistributed prefixes has crossed the system threshold {threshold}% of the limit ({limit}), the current number of redistributed prefixes are ({numeric-value})";
    dn-events-extensions:event-corrective-action-string "No corrective action.";
    dn-events-extensions:event-trigger-component-string "ospfv3";
    dn-events-extensions:event-group "OSPFv3";
    leaf threshold {
      type uint8;
      description
        "Threshold percent";
    }
    leaf numeric-value {
      type uint16;
      description
        "Current number of OSPFv3 redistributed prefixes";
    }
    leaf limit {
      type uint16;
      description
        "The accumulated OSPFv3 redistributed prefixes scale on all address-families";
    }
  }

  notification OSPFv3_MAXIMUM_REDISTRIBUTED_PREFIXES_THRESHOLD_CLEARED {
    description
      "The number of OSPFv3 redistributed prefixes is below the system threshold.";
    dn-events-extensions:event-severity-level "Info";
    dn-events-extensions:event-message-string "Number of OSPFv3 redistributed prefixes is below the system threshold {threshold}% of the limit ({limit}), the current number of redistributed prefixes are ({numeric-value})";
    dn-events-extensions:event-corrective-action-string "This is informational, no corrective action required.";
    dn-events-extensions:event-trigger-component-string "ospfv3";
    dn-events-extensions:event-group "OSPFv3";
    leaf threshold {
      type uint8;
      description
        "Threshold percent";
    }
    leaf numeric-value {
      type uint16;
      description
        "Current number of OSPFv3 redistributed prefixes";
    }
    leaf limit {
      type uint16;
      description
        "The accumulated OSPFv3 redistributed prefixes scale on all address-families";
    }
  }

  notification OSPFv3_GRACEFUL_RESTART_STATUS_CHANGE {
    description
      "The OSPFv3 Graceful Restart state has changed.";
    dn-events-extensions:event-severity-level "Info";
    dn-events-extensions:event-message-string "OSPFv3 router {router-id} process restarted. Graceful Restart state {gr-state} {gr-sub-state}. Graceful Restart grace period {grace-period} seconds";
    dn-events-extensions:event-corrective-action-string "This is informational, no corrective action required.";
    dn-events-extensions:event-trigger-component-string "ospfv3";
    dn-events-extensions:event-group "OSPFv3";
    leaf router-id {
      type string;
      description
        "OSPF Router ID";
    }
    leaf gr-state {
      type enumeration {
        enum not-restarting {
          value 1;
        }
        enum planned-restart {
          value 2;
        }
        enum unplanned-restart {
          value 3;
        }
      }
      description
        "Current status of OSPF graceful restart.";
    }
    leaf grace-period {
      type uint16 {
        range "60..1800";
      }
      description
        "Configured OSPF graceful restart timeout interval.";
    }
    leaf gr-sub-state {
      type enumeration {
        enum none {
          value 1;
        }
        enum in-progress {
          value 2;
        }
        enum completed {
          value 3;
        }
        enum time-out {
          value 4;
        }
        enum topology-changed {
          value 5;
        }
      }
      description
        "Describes the outcome of the last attempt at a
         graceful restart.  If the value is 'none', no restart
         has yet been attempted.  If the value is 'inProgress',
         a restart attempt is currently underway.";
    }
  }

  notification ENT_CONFIG_CHANGE {
    description
      "Physical entity was added, removed or changed";
    dn-events-extensions:event-severity-level "Info";
    dn-events-extensions:event-message-string "Physical entity was added, removed or changed";
    dn-events-extensions:event-corrective-action-string "This is informational, no corrective action required.";
    dn-events-extensions:event-trigger-component-string "WB Agent";
    dn-events-extensions:event-group "Platform";
    dn-events-extensions:event-snmp-trap-name "entConfigChange";
    dn-events-extensions:event-snmp-trap-oid ".1.3.6.1.2.1.47.2.0.1";
  }

  notification OSPFV3_MAXIMUM_ADJACENCIES_LIMIT_REACHED {
    description
      "The number of OSPFv3 adjacencies has reached the configured system limit.";
    dn-events-extensions:event-severity-level "Warning";
    dn-events-extensions:event-message-string "Number of OSPFv3 adjacencies has reached system limit of {limit}";
    dn-events-extensions:event-corrective-action-string "No corrective action.";
    dn-events-extensions:event-trigger-component-string "ospfv3";
    dn-events-extensions:event-group "OSPFv3";
    leaf limit {
      type uint16;
      description
        "The accumulated adjacencies scale";
    }
  }

  notification OSPFV3_MAXIMUM_ADJACENCIES_LIMIT_CLEARED {
    description
      "OSPFv3 adjacencies have been removed, the number of OSPFv3 adjacencies is below the system limit.";
    dn-events-extensions:event-severity-level "Info";
    dn-events-extensions:event-message-string "Number of OSPFv3 adjacencies is below the system limit of {limit} adjacencies";
    dn-events-extensions:event-corrective-action-string "This is informational, no corrective action required.";
    dn-events-extensions:event-trigger-component-string "ospfv3";
    dn-events-extensions:event-group "OSPFv3";
    leaf limit {
      type uint16;
      description
        "The accumulated adjacencies scale";
    }
  }

  notification OSPFV3_MAXIMUM_ADJACENCIES_THRESHOLD_EXCEEDED {
    description
      "The number of OSPFv3 adjacencies has crossed the system threshold.";
    dn-events-extensions:event-severity-level "Notice";
    dn-events-extensions:event-message-string "Number of OSPFv3 adjacencies has crossed the system threshold {threshold}% limit of {limit}, the number of OSPFv3 adjacencies are ({numeric-value})";
    dn-events-extensions:event-corrective-action-string "No corrective action.";
    dn-events-extensions:event-trigger-component-string "ospfv3";
    dn-events-extensions:event-group "OSPFv3";
    leaf threshold {
      type uint8;
      description
        "Threshold percent";
    }
    leaf numeric-value {
      type uint16;
      description
        "Current number of ospfv3 adjacencies";
    }
    leaf limit {
      type uint16;
      description
        "The accumulated adjacencies scale";
    }
  }

  notification OSPFV3_MAXIMUM_ADJACENCIES_THRESHOLD_CLEARED {
    description
      "The number of OSPFv3 adjacencies is below the system threshold.";
    dn-events-extensions:event-severity-level "Info";
    dn-events-extensions:event-message-string "Number of OSPFv3 adjacencies is below the system threshold {threshold}% of the limit ({limit}), the current number of OSPFv3 adjacencies are ({numeric-value})";
    dn-events-extensions:event-corrective-action-string "This is informational, no corrective action required.";
    dn-events-extensions:event-trigger-component-string "ospfv3";
    dn-events-extensions:event-group "OSPFv3";
    leaf threshold {
      type uint8;
      description
        "Threshold percent";
    }
    leaf numeric-value {
      type uint16;
      description
        "Current number of ospfv3 adjacencies";
    }
    leaf limit {
      type uint16;
      description
        "The accumulated adjacencies scale";
    }
  }

  notification OSPFV3_MAXIMUM_ROUTES_LIMIT_REACHED {
    description
      "The number of OSPFv3 routes has reached the system limit.";
    dn-events-extensions:event-severity-level "Warning";
    dn-events-extensions:event-message-string "Number of OSPFv3 routes has reached the system limit of {limit} routes";
    dn-events-extensions:event-corrective-action-string "No corrective action.";
    dn-events-extensions:event-trigger-component-string "ospfv3";
    dn-events-extensions:event-group "OSPFv3";
    leaf limit {
      type uint16;
      description
        "The accumulated routes scale";
    }
  }

  notification OSPFV3_MAXIMUM_ROUTES_LIMIT_CLEARED {
    description
      "Routes have been removed, the number of OSPFv3 routes is below the system limit.";
    dn-events-extensions:event-severity-level "Info";
    dn-events-extensions:event-message-string "Number of OSPFv3 routes is below the system limit of {limit} routes";
    dn-events-extensions:event-corrective-action-string "This is informational, no corrective action required.";
    dn-events-extensions:event-trigger-component-string "ospfv3";
    dn-events-extensions:event-group "OSPFv3";
    leaf limit {
      type uint16;
      description
        "The accumulated routes scale";
    }
  }

  notification OSPFV3_MAXIMUM_ROUTES_THRESHOLD_EXCEEDED {
    description
      "The number of OSPFv3 routes has crossed the system threshold.";
    dn-events-extensions:event-severity-level "Notice";
    dn-events-extensions:event-message-string "Number of OSPFv3 routes has crossed the system threshold {threshold}% of the limit ({limit}), the current number of routes are ({numeric-value})";
    dn-events-extensions:event-corrective-action-string "No corrective action.";
    dn-events-extensions:event-trigger-component-string "ospfv3";
    dn-events-extensions:event-group "OSPFv3";
    leaf threshold {
      type uint8;
      description
        "Threshold percent";
    }
    leaf numeric-value {
      type uint16;
      description
        "Current number of ospfv3 routes";
    }
    leaf limit {
      type uint16;
      description
        "The accumulated routes scale";
    }
  }

  notification OSPFV3_MAXIMUM_ROUTES_THRESHOLD_CLEARED {
    description
      "The number of OSPFv3 routes is below the system threshold.";
    dn-events-extensions:event-severity-level "Info";
    dn-events-extensions:event-message-string "Number of OSPFv3 routes is below the system threshold {threshold}% of the limit ({limit}), the current number of routes are ({numeric-value})";
    dn-events-extensions:event-corrective-action-string "This is informational, no corrective action required.";
    dn-events-extensions:event-trigger-component-string "ospfv3";
    dn-events-extensions:event-group "OSPFv3";
    leaf threshold {
      type uint8;
      description
        "Threshold percent";
    }
    leaf numeric-value {
      type uint16;
      description
        "Current number of ospfv3 routes";
    }
    leaf limit {
      type uint16;
      description
        "The accumulated routes scale";
    }
  }

  notification OSPFV3_NSR_RECOVERED {
    description
      "The system performed an OSPFv3 Non-Stop Routing recovery due to a restart of the ospf6d process.";
    dn-events-extensions:event-severity-level "Notice";
    dn-events-extensions:event-message-string "OSPFv3 Non-Stop Routing recovery was performed due to a restart of the ospf6d process";
    dn-events-extensions:event-corrective-action-string "This is informational, no corrective action required.";
    dn-events-extensions:event-trigger-component-string "ospfv3";
    dn-events-extensions:event-group "OSPFv3";
  }

  notification OSPFV3_NSR_RECOVERY_FAILED {
    description
      "The OSPFv3 process failed to recover in Non-Stop Routing mode.";
    dn-events-extensions:event-severity-level "Warning";
    dn-events-extensions:event-message-string "Ospf6d process failed to recover in Non-Stop Routing mode";
    dn-events-extensions:event-corrective-action-string "Verify NSR readiness prior to the failure event. If the database was synchronized prior to the failure event, contact Customer Support.";
    dn-events-extensions:event-trigger-component-string "ospfv3";
    dn-events-extensions:event-group "OSPFv3";
  }

  // System diagnostics events

  notification SYSTEM_DIAG_PUNT_DATAPATH_THRESHOLD_REACHED {
    description
      "System diagnostics test failed, number of executed tests passed the failure threshold.";
    dn-events-extensions:event-severity-level "Warning";
    dn-events-extensions:event-message-string "Test failed on NCP {ncp-id}, failure threshold {failure-threshold} was exceeded";
    dn-events-extensions:event-corrective-action-string "check the logs for PUNT_DATAPATH keyword.";
    dn-events-extensions:event-trigger-component-string "Diagnostics-manager";
    dn-events-extensions:event-group "Diagnostics";
    leaf ncp-id {
      type uint8;
      description
        "NCP id";
    }
    leaf failure-threshold {
      type uint8;
      description
        "The number of times a test can fail consecutively and it won't be considered as test failure";
    }
  }

  notification SYSTEM_DIAG_PUNT_DATAPATH_THRESHOLD_CLEARED {
    description
      "System diagnostics test now is successfully running.";
    dn-events-extensions:event-severity-level "Info";
    dn-events-extensions:event-message-string "Number of lost diagnostics packets is below the consecutive threshold {failure-threshold} on NCP {ncp-id}";
    dn-events-extensions:event-corrective-action-string "This is informational, no corrective action required.";
    dn-events-extensions:event-trigger-component-string "Diagnostics-manager";
    dn-events-extensions:event-group "Diagnostics";
    leaf ncp-id {
      type uint8;
      description
        "NCP id";
    }
    leaf failure-threshold {
      type uint8;
      description
        "threshold number of consecutive failed packets for which system events will be generated";
    }
  }

  //Golden config events

  notification GOLDEN_CONFIG_GENERATION_REQUEST {
    description
      "Golden configuration file generation request was triggered by the user.";
    dn-events-extensions:event-severity-level "Notice";
    dn-events-extensions:event-message-string "Golden configuration file generation requested on {node-type} {node-id}";
    dn-events-extensions:event-corrective-action-string "No corrective action is required.";
    dn-events-extensions:event-trigger-component-string "Cluster Manager";
    dn-events-extensions:event-group "System";
    leaf node-type {
      type string;
      description
        "Node type";
    }
    leaf node-id {
      type string;
      description
        "Node ID";
    }
  }

  notification GOLDEN_CONFIG_GENERATION_FAILED {
    description
      "Golden configuration file generation failed.";
    dn-events-extensions:event-severity-level "Error";
    dn-events-extensions:event-message-string "Golden configuration file generation failed on {node-type} {node-id}";
    dn-events-extensions:event-corrective-action-string "Check logs for error indication.";
    dn-events-extensions:event-trigger-component-string "Cluster Manager";
    dn-events-extensions:event-group "System";
    leaf node-type {
      type string;
      description
        "Node type";
    }
    leaf node-id {
      type string;
      description
        "Node ID";
    }
  }

  notification LOAD_GOLDEN_CONFIG_FAILED {
    description
      "Golden configuration load operation failed.";
    dn-events-extensions:event-severity-level "Error";
    dn-events-extensions:event-message-string "Golden configuration file is either missing or corrupted on {node-type} {node-id}";
    dn-events-extensions:event-corrective-action-string "Check golden configuration file.";
    dn-events-extensions:event-trigger-component-string "Cluster Manager";
    dn-events-extensions:event-group "System";
    leaf node-type {
      type string;
      description
        "Node type";
    }
    leaf node-id {
      type string;
      description
        "Node ID";
    }
  }

  notification LOAD_GOLDEN_CONFIG_DETECTED {
    description
      "Golden configuration load was triggered by the user. Load triggered either by a long push button press or by calling a remote admin privilidged command.";
    dn-events-extensions:event-severity-level "Notice";
    dn-events-extensions:event-message-string "Golden configuration load was triggered by the user on {node-type} {node-id} using {trigger-type}";
    dn-events-extensions:event-corrective-action-string "No corrective action is required.";
    dn-events-extensions:event-trigger-component-string "Cluster Manager";
    dn-events-extensions:event-group "System";
    leaf node-type {
      type string;
      description
        "Node type";
    }
    leaf node-id {
      type string;
      description
        "Node ID";
    }
    leaf trigger-type {
      type enumeration {
        enum remote_command;
        enum push_button;
      }
      description
        "Golden config trigger type";
    }
  }

  //Telnet events

  notification TELNET_SESSION_LOGIN_DENIED {
    description
      "Telnet has rejected a new session to the system due to client-list configuration.";
    dn-events-extensions:event-severity-level "Notice";
    dn-events-extensions:event-message-string "Telnet login attempt from remote host {remote-host} has been rejected due to client-list configuration";
    dn-events-extensions:event-corrective-action-string "This is informational, no corrective action required.";
    dn-events-extensions:event-trigger-component-string "CLI";
    dn-events-extensions:event-group "Management";
    leaf remote-host {
      type string;
      description
        "Remote host address, can be an IP address or as hostname";
    }
  }

  notification TELNET_SESSION_LIMIT_CLEARED {
    description
      "The number of concurrent Telnet sessions to the system is below the configured maximum number of connections.";
    dn-events-extensions:event-severity-level "Info";
    dn-events-extensions:event-message-string "Number of Telnet sessions is below the configured maximum ({max-sessions})";
    dn-events-extensions:event-corrective-action-string "This is informational, no corrective action required.";
    dn-events-extensions:event-trigger-component-string "CLI";
    dn-events-extensions:event-group "Management";
    leaf max-sessions {
      type uint8;
      description
        "Maximum number of sessions";
    }
  }

  notification TELNET_SESSION_LIMIT_REACHED {
    description
      "The number of concurrent Telnet sessions to the system has reached the maximum number of sessions. No new Telnet sessions can be established.";
    dn-events-extensions:event-severity-level "Warning";
    dn-events-extensions:event-message-string "Number of Telnet sessions has reached the configured maximum ({max-sessions})";
    dn-events-extensions:event-corrective-action-string
      "<p>Terminate active Telnet sessions to the system:</p>
       <ol>
       <li>Run command 'show system telnet sessions' to view the existing Telnet sessions.</li>
       <li>Select a session-id for the connection you want to terminate.</li>
       <li>Run the command 'clear telnet session [session-id]'.</li>
       </ol>";
    dn-events-extensions:event-trigger-component-string "CLI";
    dn-events-extensions:event-group "Management";
    leaf max-sessions {
      type uint8;
      description
        "Maximum number of sessions";
    }
  }

  notification TELNET_SESSION_CLOSED {
    description
      "The user indicated closed the Telnet session via the remote host.";
    dn-events-extensions:event-severity-level "Info";
    dn-events-extensions:event-message-string "user {user-name} closed the Telnet session {session-id} (remote host {remote-host})";
    dn-events-extensions:event-corrective-action-string "This is informational, no corrective action required.";
    dn-events-extensions:event-trigger-component-string "CLI";
    dn-events-extensions:event-group "Management";
    leaf user-name {
      type string;
      description
        "System user-name";
    }
    leaf remote-host {
      type string;
      description
        "Remote host address, can be an IP address or as hostname";
    }
    leaf session-id {
      type uint16;
      description
        "Session id";
    }
  }

  notification TELNET_SESSION_LOGIN {
    description
      "The user and remote host indicated has logged into the system using Telnet.";
    dn-events-extensions:event-severity-level "Info";
    dn-events-extensions:event-message-string "user {user-name} has logged in using Telnet (remote host {remote-host})";
    dn-events-extensions:event-corrective-action-string "This is informational, no corrective action required.";
    dn-events-extensions:event-trigger-component-string "CLI";
    dn-events-extensions:event-group "Management";
    leaf user-name {
      type string;
      description
        "System user-name";
    }
    leaf remote-host {
      type string;
      description
        "Remote host address, can be an IP address or as hostname";
    }
  }

  notification TELNET_SESSION_TERMINATED {
    description
      "The Telnet session to system was terminated by the user indicated using the command 'clear telnet session'.";
    dn-events-extensions:event-severity-level "Notice";
    dn-events-extensions:event-message-string "Telnet session {session-id} (remote host {remote-host}) terminated by user {user-name}";
    dn-events-extensions:event-corrective-action-string "No corrective action.";
    dn-events-extensions:event-trigger-component-string "CLI";
    dn-events-extensions:event-group "Management";
    leaf user-name {
      type string;
      description
        "System user-name";
    }
    leaf remote-host {
      type string;
      description
        "Remote host address, can be an IP address or as hostname";
    }
    leaf session-id {
      type uint16;
      description
        "Session id";
    }
  }

  notification TELNET_SESSION_TIMEOUT {
    description
      "The Telnet session to system was terminated by the system due to session inactivity.";
    dn-events-extensions:event-severity-level "Info";
    dn-events-extensions:event-message-string "Telnet session {session-id} (remote host {remote-host}) was terminated due to timeout";
    dn-events-extensions:event-corrective-action-string "This is informational, no corrective action required.";
    dn-events-extensions:event-trigger-component-string "CLI";
    dn-events-extensions:event-group "Management";
    leaf remote-host {
      type string;
      description
        "Remote host address, can be an IP address or as hostname";
    }
    leaf session-id {
      type uint16;
      description
        "Session id";
    }
  }

  notification TELNET_MAXIMUM_SESSION_LIMIT_REJECT {
    description
      "A new Telnet session to the system was rejected since the number of concurrent Telnet sessions has reached the configured limit.";
    dn-events-extensions:event-severity-level "Notice";
    dn-events-extensions:event-message-string "A new Telnet session of user {user-name} from remote host {remote-host} has been rejected since the number of concurrent active Telnet sessions has reached the configured limit of {max-sessions}";
    dn-events-extensions:event-corrective-action-string
      "<p>Terminate some active Telnet sessions to the system:</p>
       <ol>
       <li>Run command 'show system telnet sessions' to view the existing telnet sessions.</li>
       <li>Select a session-id for the connection you want to terminate.</li>
       <li>Run the command 'clear telnet session [session-id]'.</li>
       </ol>";
    dn-events-extensions:event-trigger-component-string "CLI";
    dn-events-extensions:event-group "Management";
    leaf max-sessions {
      type uint8;
      description
        "Maximum number of sessions";
    }
    leaf user-name {
      type string;
      description
        "System user-name";
    }
    leaf remote-host {
      type string;
      description
        "Remote host address, can be an IP address or as hostname";
    }
  }

  notification TELNET_SESSION_LOGIN_LOCKED {
    description
      "A new Telnet session by the user indicated was rejected due to maximum number of login attempts. The user must wait for the holdoff period.";
    dn-events-extensions:event-severity-level "Notice";
    dn-events-extensions:event-message-string "Maximum number of login attempts ({login-attempts}) was reached by user {user-name}";
    dn-events-extensions:event-corrective-action-string "Wait for holdoff time defined by 'system login session-holdoff'.";
    dn-events-extensions:event-trigger-component-string "CLI";
    dn-events-extensions:event-group "Management";
    leaf user-name {
      type string;
      description
        "System user-name";
    }
    leaf login-attempts {
      type uint8;
      description
        "Maximum number of failure logins";
    }
  }

  notification TELNET_SESSION_LOGIN_FAILED {
    description
      "The user login attempt was rejected due to incorrect credentials.";
    dn-events-extensions:event-severity-level "Info";
    dn-events-extensions:event-message-string "user {user-name} login attempt from remote host {remote-host} rejected due to incorrect credentials";
    dn-events-extensions:event-corrective-action-string "This is informational, no corrective action required.";
    dn-events-extensions:event-trigger-component-string "CLI";
    dn-events-extensions:event-group "Management";
    leaf user-name {
      type string;
      description
        "System user-name";
    }
    leaf remote-host {
      type string;
      description
        "Remote host address, can be an IP address or as hostname";
    }
  }

  notification TELNET_SESSION_TIMEOUT_CONFIG {
    description
      "The user indicated changed the Telnet session timeout parameter.";
    dn-events-extensions:event-severity-level "Notice";
    dn-events-extensions:event-message-string "User {user-name} has changed Telnet Session timeout parameter";
    dn-events-extensions:event-corrective-action-string "No corrective action.";
    dn-events-extensions:event-trigger-component-string "Transaction-manager";
    dn-events-extensions:event-group "Management";
    leaf user-name {
      type string;
      description
        "System user-name";
    }
  }

  notification TELNET_CLIENT_SESSION_TERMINATED {
    description
      "The Telnet client session was terminated by the user indicated using the command 'clear telnet session'.";
    dn-events-extensions:event-severity-level "Notice";
    dn-events-extensions:event-message-string "Telnet client session {session-id} (remote host {remote-host}) was terminated by user {user-name}";
    dn-events-extensions:event-corrective-action-string "No corrective action.";
    dn-events-extensions:event-trigger-component-string "CLI";
    dn-events-extensions:event-group "Management";
    leaf user-name {
      type string;
      description
        "System user-name";
    }
    leaf remote-host {
      type string;
      description
        "Remote host address, can be an IP address or as hostname";
    }
    leaf session-id {
      type uint16;
      description
        "Session id";
    }
  }

  notification TELNET_CLIENT_CONFIG {
    description
      "The user indicated changed the Telnet client capability.";
    dn-events-extensions:event-severity-level "Info";
    dn-events-extensions:event-message-string "User {user-name} changed Telnet client capability to {client-state}";
    dn-events-extensions:event-corrective-action-string "This is informational, no corrective action required";
    dn-events-extensions:event-trigger-component-string "Transaction-manager";
    dn-events-extensions:event-group "Management";
    leaf client-state {
      type enumeration {
        enum enabled;
        enum disabled;
      }
      description
        "Telnet client configuration state";
    }
    leaf user-name {
      type string;
      description
        "System user-name";
    }
  }

  notification TELNET_SERVER_CONFIG {
    description
      "The user indicated changed the Telnet server capability.";
    dn-events-extensions:event-severity-level "Info";
    dn-events-extensions:event-message-string "User {user-name} changed Telnet server capability to {server-state}";
    dn-events-extensions:event-corrective-action-string "This is informational, no corrective action required.";
    dn-events-extensions:event-trigger-component-string "Transaction-manager";
    dn-events-extensions:event-group "Management";
    leaf server-state {
      type enumeration {
        enum enabled;
        enum disabled;
      }
      description
        "Telnet server configuration state";
    }
    leaf user-name {
      type string;
      description
        "System user-name";
    }
  }

  notification TELNET_SERVER_CLIENT_LIST_CONFIG {
    description
      "The list of restricted users for the Telnet server was configured/updated.";
    dn-events-extensions:event-severity-level "Notice";
    dn-events-extensions:event-message-string "List of restricted users for Telnet server was configured/updated";
    dn-events-extensions:event-corrective-action-string "No corrective action.";
    dn-events-extensions:event-trigger-component-string "Transaction-manager";
    dn-events-extensions:event-group "Management";
  }

  notification PLATFORM_I2C_BUS_FAILED {
    description
      "The platform's I2C bus has failed. The system ports cannot be accessed.";
    dn-events-extensions:event-severity-level "Critical";
    dn-events-extensions:event-message-string "System detected I2C bus failure on {node-type} {node-id} port {port-id}. Detailed information: {details}";
    dn-events-extensions:event-corrective-action-string "Resetting i2c bus and isolating affected port. Please remove (replace) the problematic module.";
    dn-events-extensions:event-trigger-component-string "WB Agent";
    dn-events-extensions:event-group "Platform";
    leaf node-type {
      type string;
      description
        "Node type";
    }
    leaf node-id {
      type string;
      description
        "Node ID";
    }
    leaf port-id {
      type string;
      description
        "Port ID";
    }
    leaf details {
      type string;
      description
        "Details of specific problematic module";
    }
  }

  notification PLATFORM_I2C_BUS_RECOVERY_PROCEDURE_ACTIVATED {
    description
      "The platform's I2C bus recovery procedure was activated.";
    dn-events-extensions:event-severity-level "Info";
    dn-events-extensions:event-message-string "System I2C bus recovery procedure activated on {node-type} {node-id} due to {port-id} I2C bus failure.";
    dn-events-extensions:event-corrective-action-string "No corrective action.";
    dn-events-extensions:event-trigger-component-string "WB Agent";
    dn-events-extensions:event-group "Platform";
    leaf node-type {
      type string;
      description
        "Node type";
    }
    leaf node-id {
      type string;
      description
        "Node ID";
    }
    leaf port-id {
      type string;
      description
        "Port ID";
    }
  }

  notification PLATFORM_THERMAL_SHUTDOWN_AUTO_POWER_UP_MODE_CHANGE_FAILED {
    description
      "The platform's BMC thermal shutdown auto-restart mode change has failed. ";
    dn-events-extensions:event-severity-level "Warning";
    dn-events-extensions:event-message-string "Failure setting the mode of automatic platform restart after thermal shutdown to {state} on {node-type} {node-id}. Reason: {reason}";
    dn-events-extensions:event-corrective-action-string "Verify that the configuration change is supported by the platform's BMC.";
    dn-events-extensions:event-trigger-component-string "WB Agent";
    dn-events-extensions:event-group "Platform";
    leaf state {
      type enumeration {
        enum disabled;
        enum enabled;
      }
      description
        "Platform's BMC automatic power up after thermal shutdown mode";
    }
    leaf node-type {
      type string;
      description
        "Node type";
    }
    leaf node-id {
      type string;
      description
        "Node ID";
    }
    leaf port-id {
      type string;
      description
        "Port ID";
    }
    leaf reason {
      type string;
      description
        "The reason for failing to set the BMC mode of automatic power up after thermal shutdown";
    }
  }

  // L2VPN events

  notification PSEUDOWIRE_DOWN {
    description
      "The referenced Pseudowire connection changed to a 'down' state and cannot be used to forward traffic.";
    dn-events-extensions:event-severity-level "Warning";
    dn-events-extensions:event-message-string "Pseudowire to address {neighbor-address}, ID {pw-id}, state is {pw-new-state}, reason: {down-reason}. Pseudowire part of {service-type} {service-name}";
    dn-events-extensions:event-corrective-action-string "Verify the configuration settings, AC state, and alignment with the Pseudowire remote-end settings.";
    dn-events-extensions:event-trigger-component-string "L2VPN";
    dn-events-extensions:event-group "L2VPN";
    leaf neighbor-address {
      description
        "PW remote-end address";
      type string;
    }
    leaf pw-id {
      description
        "PW configured identifier";
      type uint32;
    }
    leaf pw-new-state {
      description
        "PW new state, either Down or Admin-Down";
      type enumeration {
        enum Down;
        enum Admin-Down;
      }
    }
    leaf down-reason {
      description
        "String reason of why PW change to Down state";
      type string;
    }
    leaf service-type {
      description
        "Type of L2VPN service this PW belongs to";
      type enumeration {
        enum VPWS;
        enum VPLS;
        enum PWHE;
      }
    }
    leaf service-name {
      description
        "Name of L2VPN service this PW belongs to";
      type string;
    }
  }

  notification PSEUDOWIRE_UP {
    description
      "The referenced Pseudowire connection changed to an 'up' state and can be used to forward traffic.";
    dn-events-extensions:event-severity-level "Info";
    dn-events-extensions:event-message-string "Pseudowire to address {neighbor-address}, ID {pw-id}, state is Up. Pseudowire part of {service-type} {service-name}";
    dn-events-extensions:event-corrective-action-string "This is informational, no corrective action required.";
    dn-events-extensions:event-trigger-component-string "L2VPN";
    dn-events-extensions:event-group "L2VPN";
    leaf neighbor-address {
      description
        "PW remote-end address";
      type string;
    }
    leaf pw-id {
      description
        "PW configured identifier";
      type uint32;
    }
    leaf service-type {
      description
        "Type of L2VPN service this PW belongs to";
      type enumeration {
        enum VPWS;
        enum VPLS;
        enum PWHE;
      }
    }
    leaf service-name {
      description
        "Name of L2VPN service this PW belongs to";
      type string;
    }
  }

  notification EVPN_VPWS_SERVICE_NOT_ESTABLISHED {
    description
      "The referenced EVPN-VPWS service changed to a 'down' state and cannot be used to forward traffic.";
    dn-events-extensions:event-severity-level "Warning";
    dn-events-extensions:event-message-string "The EVPN-VPWS service {service-name} - Local-ID {local-vpws-service-id}, Remote-ID {remote-vpws-service-id} state is {pw-new-state}.";
    dn-events-extensions:event-corrective-action-string "Verify the configuration settings, AC state, and alignment with the Pseudowire remote-end settings.";
    dn-events-extensions:event-trigger-component-string "L2VPN";
    dn-events-extensions:event-group "L2VPN";
    leaf service-name {
      description
        "Name of L2VPN service this PW belongs to";
      type string;
    }
    leaf local-vpws-service-id {
      description
        "PW configured identifier";
      type uint32;
    }
    leaf remote-vpws-service-id {
      description
        "PW configured identifier";
      type uint32;
    }
    leaf pw-new-state {
      description
        "PW new state, either Down or Admin-Down";
      type enumeration {
        enum Down;
        enum Admin-Down;
      }
    }
  }

  notification EVPN_VPWS_SERVICE_ESTABLISHED {
    description
      "The referenced EVPN-VPWS service changed to an 'up' state and can be used to forward traffic.";
    dn-events-extensions:event-severity-level "Info";
    dn-events-extensions:event-message-string "The EVPN-VPWS service {service-name} - Local-ID {local-vpws-service-id}, Remote-ID {remote-vpws-service-id} state is UP.";
    dn-events-extensions:event-corrective-action-string "This is informational, no corrective action required.";
    dn-events-extensions:event-trigger-component-string "L2VPN";
    dn-events-extensions:event-group "L2VPN";
    leaf service-name {
      description
        "Name of L2VPN service this PW belongs to";
      type string;
    }
    leaf local-vpws-service-id {
      description
        "PW configured identifier";
      type uint32;
    }
    leaf remote-vpws-service-id {
      description
        "PW configured identifier";
      type uint32;
    }
  }

  // EVPN-VPWS-FXC

  notification EVPN_VPWS_FXC_SUB_SERVICE_NOT_ESTABLISHED {
    description
      "The referenced EVPN-VPWS-FXC sub-service changed to a 'down' state and cannot be used to forward traffic.";
    dn-events-extensions:event-severity-level "Warning";
    dn-events-extensions:event-message-string "The EVPN-VPWS-FXC sub-service {service-name}:{interface-name} state is {pw-new-state}.";
    dn-events-extensions:event-corrective-action-string "Verify the configuration settings, AC state, and alignment with the Pseudowire remote-end settings.";
    dn-events-extensions:event-trigger-component-string "L2VPN";
    dn-events-extensions:event-group "L2VPN";
    leaf service-name {
      description
        "Name of L2VPN service this PW belongs to";
      type string;
    }
    leaf interface-name {
      type string;
      description
        "sub-service interface name";
    }
    leaf pw-new-state {
      description
        "PW new state, either Down or Admin-Down";
      type enumeration {
        enum Down;
        enum Admin-Down;
      }
    }
  }

  notification MPLS_BGP_L2VPN_VPLS_LABEL_ALLOCATION_FAILED {
    description
      "Cannot allocate labels for BGP-L2VPN services because no contiguous block exists in the label pool.";
    dn-events-extensions:event-severity-level "Error";
    dn-events-extensions:event-message-string "Cannot allocate label block of {block-size-to-allocate} for instance {instance-type} '{instance-name}' - no contiguous block exists in the pool. This local NLRI will not be advertised to any peer.";
    dn-events-extensions:event-corrective-action-string "Modify the label block size and restart the system.";
    dn-events-extensions:event-trigger-component-string "L2VPN";
    dn-events-extensions:event-group "L2VPN";
    leaf block-size-to-allocate {
      description
        "block size to allocate";
      type uint32;
    }
    leaf instance-type {
      description
        "Type of L2VPN service this PW belongs to";
      type enumeration {
        enum EVPN-VPWS-SEAMLESS-INTEGRATION;
        enum EVPN-SEAMLESS-INTEGRATION;
      }
    }
    leaf instance-name {
      description
        "Name of L2VPN service this PW belongs to";
      type string;
    }
  }

  notification EVPN_VPWS_FXC_SUB_SERVICE_ESTABLISHED {
    description
      "The referenced EVPN-VPWS-FXC sub-service changed to an 'up' state and can be used to forward traffic.";
    dn-events-extensions:event-severity-level "Info";
    dn-events-extensions:event-message-string "The EVPN-VPWS-FXC sub-service {service-name}:{interface-name} state is UP.";
    dn-events-extensions:event-corrective-action-string "This is informational, no corrective action required.";
    dn-events-extensions:event-trigger-component-string "L2VPN";
    dn-events-extensions:event-group "L2VPN";
    leaf service-name {
      description
        "Name of L2VPN service this PW belongs to";
      type string;
    }
    leaf interface-name {
      type string;
      description
        "sub-service interface name";
    }
  }

  // Multihoming

  notification MULTIHOMING_ETHERNET_SEGMENT_CONFIGURATION_MISMATCH_DETECTED {
    description
      "The referenced service that is configured with a multihomed AC has detected a configuration mismatch with a Peer PE.";
    dn-events-extensions:event-severity-level "Warning";
    dn-events-extensions:event-message-string "The service {service-name} with multihomed interface {interface-name} has detected a mismatch, mismatch reason: {mismatch-reason} ";
    dn-events-extensions:event-corrective-action-string "Verify the local configuration settings, and align with the Peer PE settings.";
    dn-events-extensions:event-trigger-component-string "L2VPN";
    dn-events-extensions:event-group "L2VPN";
    leaf service-name {
      description
        "Name of L2VPN service";
      type string;
    }
    leaf interface-name {
      type string;
      description
        "Multihomed interface name";
    }
    leaf mismatch-reason {
      description
        "String reason detailing the mismatch";
      type string;
    }
  }

  notification MULTIHOMING_ETHERNET_SEGMENT_CONFIGURATION_MISMATCH_CLEARED {
    description
      "The referenced service has detected the clearance of the configuration mismatch.";
    dn-events-extensions:event-severity-level "Info";
    dn-events-extensions:event-message-string "The service {service-name} with multihomed interface {interface-name} has cleared the mismatch";
    dn-events-extensions:event-corrective-action-string "This is informational, no corrective action required.";
    dn-events-extensions:event-trigger-component-string "L2VPN";
    dn-events-extensions:event-group "L2VPN";
    leaf service-name {
      description
        "Name of L2VPN service";
      type string;
    }
    leaf interface-name {
      type string;
      description
        "Multihomed interface name";
    }
  }

  notification MULTIHOMING_ETHERNET_SEGMENT_LACP_ESI_CONFLICT_DETECTED {
    description
      "A LACP type ESI conflict has been detected on the referenced multihomed AC bundles - multiple CEs with same system-id+port-key.";
    dn-events-extensions:event-severity-level "Warning";
    dn-events-extensions:event-message-string "The ESI {esi} on multihomed {bundle-1-name} is identical to that on {bundle-2-name} ";
    dn-events-extensions:event-corrective-action-string "Verify the CE LACP configuration, or set the ESI using type arbitrary";
    dn-events-extensions:event-trigger-component-string "L2VPN";
    dn-events-extensions:event-group "L2VPN";
    leaf esi {
      description
        "The ESI value - generated from the received CE system-id and port-key";
      type string;
    }
    leaf bundle-1-name {
      type string;
      description
        "Multihomed bundle name";
    }
    leaf bundle-2-name {
      type string;
      description
        "Multihomed bundle name";
    }
  }

  notification MULTIHOMING_ETHERNET_SEGMENT_LACP_ESI_CONFLICT_CLEARED {
    description
      "The LACP type ESI conflict has been cleared.";
    dn-events-extensions:event-severity-level "Info";
    dn-events-extensions:event-message-string "There is no longer a conflict for the bundle {bundle-name}";
    dn-events-extensions:event-corrective-action-string "This is informational, no corrective action required.";
    dn-events-extensions:event-trigger-component-string "L2VPN";
    dn-events-extensions:event-group "L2VPN";
    leaf bundle-name {
      type string;
      description
        "Multihomed bundle name";
    }
  }

  // Next-Hop Resources events ( FEC, ECMP amd SuperFEC resources events)

  notification NEXT_HOP_THRESHOLD_EXCEEDED {
    description
      "The system threshold for a next-hop resource has been crossed.";
    dn-events-extensions:event-severity-level "Notice";
    dn-events-extensions:event-message-string "NCP {ncp-id} reports that the number of {resource-name} in use has crossed the system threshold {threshold}% of the limit ({limit}), the current number of elements is ({numeric-value})";
    dn-events-extensions:event-corrective-action-string "No corrective action.";
    dn-events-extensions:event-trigger-component-string "WB Agent";
    dn-events-extensions:event-group "fib-manager";
    leaf ncp-id {
      type uint8;
      description
        "NCP id";
    }
    leaf resource-name {
      description
        "Next-Hop Resource";
      type enumeration {
        enum NEIGHBOR;
        enum NEXT_HOP_LEVEL_1_ELEMENTS;
        enum NEXT_HOP_LEVEL_2_ELEMENTS;
        enum NEXT_HOP_LEVEL_3_ELEMENTS;
        enum NEXT_HOP_PROTECTION_ELEMENTS;
        enum ECMP_NEXT_HOP_GROUPS;
        enum DESTINATION_PE;
        enum ASBR_LSP;
      }
    }
    leaf threshold {
      type uint8;
      description
        "Threshold percent";
    }
    leaf numeric-value {
      type uint32;
      description
        "Current number of the next-hop resource that are in use";
    }
    leaf limit {
      type uint32;
      description
        "The allocated number (maximum value) of the next-hop resource";
    }
  }

  notification NEXT_HOP_THRESHOLD_CLEARED {
    description
      "The next-hop resource is now below the threshold.";
    dn-events-extensions:event-severity-level "Info";
    dn-events-extensions:event-message-string "NCP {ncp-id} reports that the number of {resource-name} in use is below the threshold {threshold}% of the limit ({limit}), the current number of elements is ({numeric-value})";
    dn-events-extensions:event-corrective-action-string "This is informational, no corrective action required.";
    dn-events-extensions:event-trigger-component-string "WB Agent";
    dn-events-extensions:event-group "fib-manager";
    leaf ncp-id {
      type uint8;
      description
        "NCP id";
    }
    leaf resource-name {
      description
        "Next-Hop Resource";
      type enumeration {
        enum NEIGHBOR;
        enum NEXT_HOP_LEVEL_1_ELEMENTS;
        enum NEXT_HOP_LEVEL_2_ELEMENTS;
        enum NEXT_HOP_LEVEL_3_ELEMENTS;
        enum NEXT_HOP_PROTECTION_ELEMENTS;
        enum ECMP_NEXT_HOP_GROUPS;
        enum DESTINATION_PE;
        enum ASBR_LSP;
      }
    }
    leaf threshold {
      type uint8;
      description
        "Threshold percent";
    }
    leaf numeric-value {
      type uint32;
      description
        "Current number of the next-hop resource that are in use";
    }
    leaf limit {
      type uint32;
      description
        "The allocated number (maximum value) of the next-hop resource";
    }
  }

  // MAC Table events ( MAC_Table Threshold Exceeded and Total MAC Table Threshold exceeded )

  notification MAC_TABLE_THRESHOLD_EXCEEDED {
    description
      "The MAC Table Limit Threshold has been crossed.";
    dn-events-extensions:event-severity-level "Notice";
    dn-events-extensions:event-message-string "The number of MAC Table entries in use for the Service {name} has crossed the 90% threshold of the limit ({limit}), the current number of entries is ({numeric-value})";
    dn-events-extensions:event-corrective-action-string "No corrective action.";
    dn-events-extensions:event-trigger-component-string "fib-manager";
    dn-events-extensions:event-group "fib-manager";
    leaf name {
      type string;
      description
        "The name of the service instance";
    }
    leaf limit {
      type uint32;
      description
        "The configured MAC Table limit";
    }
    leaf numeric-value {
      type uint32;
      description
        "Current number of entries in the MAC Table of this service instance";
    }
  }

  notification MAC_TABLE_THRESHOLD_CLEARED {
    description
      "The number of MAC Table Entries is below the Threshold.";
    dn-events-extensions:event-severity-level "Info";
    dn-events-extensions:event-message-string "The number of MAC Table entries in use by the Service {name} has dropped below the 85% threshold of the limit ({limit}), the current number of entries is ({numeric-value})";
    dn-events-extensions:event-corrective-action-string "This is informational, no corrective action required.";
    dn-events-extensions:event-trigger-component-string "fib-manager";
    dn-events-extensions:event-group "fib-manager";
    leaf name {
      type string;
      description
        "The name of the service instance";
    }
    leaf limit {
      type uint32;
      description
        "The configured MAC Table limit";
    }
    leaf numeric-value {
      type uint32;
      description
        "Current number of entries in the MAC Table of this service instance";
    }
  }

  notification TOTAL_MAC_TABLE_THRESHOLD_EXCEEDED {
    description
      "The MAC Table Limit Threshold has been crossed.";
    dn-events-extensions:event-severity-level "Notice";
    dn-events-extensions:event-message-string "The total number of MAC Table entries in use for all Services has crossed the 90% threshold of the limit ({limit}), the current number of entries is ({numeric-value})";
    dn-events-extensions:event-corrective-action-string "No corrective action.";
    dn-events-extensions:event-trigger-component-string "fib-manager";
    dn-events-extensions:event-group "fib-manager";
    leaf limit {
      type uint32;
      description
        "The Total MAC Table limit";
    }
    leaf numeric-value {
      type uint32;
      description
        "Current number of MAC Table entries";
    }
  }

  notification TOTAL_MAC_TABLE_THRESHOLD_CLEARED {
    description
      "The number of MAC Table Entries is below the Threshold.";
    dn-events-extensions:event-severity-level "Info";
    dn-events-extensions:event-message-string "The total number of MAC Table entries in use by all the Services has dropped below the 85% threshold of the limit ({limit}), the current number of entries is ({numeric-value})";
    dn-events-extensions:event-corrective-action-string "This is informational, no corrective action required.";
    dn-events-extensions:event-trigger-component-string "fib-manager";
    dn-events-extensions:event-group "fib-manager";
    leaf limit {
      type uint32;
      description
        "The configured MAC Table limit";
    }
    leaf numeric-value {
      type uint32;
      description
        "Current number of MAC Table entries";
    }
  }

  notification L2_MAC_MOBILITY_STICKY_MAC_COLLISION {
    description
      "A collision has occurred on a sticky MAC address.";
    dn-events-extensions:event-severity-level "Notice";
    dn-events-extensions:event-message-string "A collision has occurred on sticky MAC {mac-address} associated with service {service-name}.";
    dn-events-extensions:event-corrective-action-string "Check configuration, check for layer-2 network loops, check BGP show for this MAC address";
    dn-events-extensions:event-trigger-component-string "RIB-manager";
    dn-events-extensions:event-group "L2VPN";
    leaf mac-address {
      type string;
      description
        "Sticky MAC address that has the collision.";
    }
    leaf service-name {
      description
        "Name of L2VPN service";
      type string;
    }
  }

  notification IP_MOBILITY_STICKY_MAC_COLLISION {
    description
      "A collision has occurred for an IP address on two different sticky MAC addresses.";
    dn-events-extensions:event-severity-level "Notice";
    dn-events-extensions:event-message-string "A collision has occurred for IP address {ip-address} on local sticky MAC {local-mac-address} associated with service {service-name}.";
    dn-events-extensions:event-corrective-action-string "Check configuration";
    dn-events-extensions:event-trigger-component-string "Routing";
    dn-events-extensions:event-group "L2VPN";
    leaf ip-address {
      type string;
      description
        "IP address that has the collision.";
    }
    leaf local-mac-address {
      type string;
      description
        "Local sticky MAC address that is associated to IP address.";
    }
    leaf service-name {
      description
        "Name of L2VPN service";
      type string;
    }
  }

  notification IP_MOBILITY_STICKY_MAC_COLLISION_WITH_NON_STICKY_LOCAL {
    description
      "A collision has occurred for an IP address on sticky MAC address and local non-sticky MAC address.";
    dn-events-extensions:event-severity-level "Notice";
    dn-events-extensions:event-message-string "A collision has occurred for IP address {ip-address} on both sticky MAC-1 {local-mac-address} and associated with service {service-name}.";
    dn-events-extensions:event-corrective-action-string "Check configuration";
    dn-events-extensions:event-trigger-component-string "Routing";
    dn-events-extensions:event-group "L2VPN";
    leaf ip-address {
      type string;
      description
        "IP address that has the collision.";
    }
    leaf local-mac-address {
      type string;
      description
        "Local non-sticky MAC address that is associated to IP address.";
    }
    leaf service-name {
      description
        "Name of L2VPN service";
      type string;
    }
  }

  notification L2_REMOTE_DEFAULT_GATEWAY_LOCAL_STICKY_MAC_COLLISION {
    description
      "A collision has occurred on a MAC address - remote received with default gateway ext community while local configured as sticky";
    dn-events-extensions:event-severity-level "Notice";
    dn-events-extensions:event-message-string "A collision has occurred on a local sticky MAC {mac-address} while remote received with default-gateway extended community associated with service {service-name}.";
    dn-events-extensions:event-corrective-action-string "Check configuration, check for layer-2 network loops, check BGP show for this MAC address";
    dn-events-extensions:event-trigger-component-string "RIB-manager";
    dn-events-extensions:event-group "L2VPN";
    leaf mac-address {
      type string;
      description
        "Sticky local MAC address while remote is default-gateway that has the collision.";
    }
    leaf service-name {
      description
        "Name of L2VPN service";
      type string;
    }
  }

  notification L2_MAC_MOBILITY_MAC_ADDRESS_SUPPRESSED {
    description
      "A MAC address has exceeded the number of allowed move events and has been suppressed";
    dn-events-extensions:event-severity-level "Warning";
    dn-events-extensions:event-message-string "The MAC {mac-address} received in service {service-name} has been suppressed, having moved {mac-move-threshold} times in {loop-detection-window-period} seconds period.";
    dn-events-extensions:event-corrective-action-string "Check configuration, check for layer-2 network loops";
    dn-events-extensions:event-trigger-component-string "fib-manager";
    dn-events-extensions:event-group "L2VPN";
    leaf mac-address {
      type string;
      description
        "MAC address that has been suppressed.";
    }
    leaf service-name {
      description
        "Name of L2VPN service";
      type string;
    }
    leaf loop-detection-window-period {
      type uint16 {
        range "1..600";
      }
      description
        "Loop Detection Window Period.";
    }
    leaf mac-move-threshold {
      type uint8 {
        range "2..30";
      }
      description
        "Number of allowed Moves within the Loop Detection Window Period";
    }
  }

  notification L2_MAC_MOBILITY_MAC_ADDRESS_PERMANENTLY_SUPPRESSED {
    description
      "A MAC address has exceeded the number of allowed move events and has been permanently suppressed";
    dn-events-extensions:event-severity-level "Warning";
    dn-events-extensions:event-message-string "The MAC {mac-address} received in service {service-name} has been permanently suppressed, having crossed the restore-cycles {restore-cycles} limit.";
    dn-events-extensions:event-corrective-action-string "Check configuration, check for layer-2 network loops";
    dn-events-extensions:event-trigger-component-string "fib-manager";
    dn-events-extensions:event-group "L2VPN";
    leaf mac-address {
      type string;
      description
        "MAC address that has been permanently suppressed.";
    }
    leaf service-name {
      description
        "Name of L2VPN service";
      type string;
    }
    leaf restore-cycles {
      type uint8 {
        range "1..10";
      }
      description
        "The number of restore-cycles allowed before permanantly suppressing the MAC address.";
    }
  }

  notification L2_MAC_MOBILITY_MAC_ADDRESS_RELEASED {
    description
      "A MAC address that was suppressed has now been released";
    dn-events-extensions:event-severity-level "Info";
    dn-events-extensions:event-message-string "The MAC {mac-address} received in service {service-name} that was suppressed, has been released due to {release-reason}.";
    dn-events-extensions:event-corrective-action-string "This is informational, no corrective action required.";
    dn-events-extensions:event-trigger-component-string "fib-manager";
    dn-events-extensions:event-group "L2VPN";
    leaf mac-address {
      type string;
      description
        "MAC address that was suppressed.";
    }
    leaf service-name {
      description
        "Name of L2VPN service";
      type string;
    }
    leaf release-reason {
      type string;
      description
        "Release Reason";
    }
  }

  notification IP_MOBILITY_IP_ADDRESS_SUPPRESSED {
    description
      "An IP address has exceeded the number of allowed move events and has been suppressed";
    dn-events-extensions:event-severity-level "Warning";
    dn-events-extensions:event-message-string "The IP {ip-address} received in service {service-name} has been suppressed, having moved {ip-move-threshold} times in {ip-loop-detection-window-period} seconds period.";
    dn-events-extensions:event-corrective-action-string "Check configuration, check for layer-3 network loops";
    dn-events-extensions:event-trigger-component-string "fib-manager";
    dn-events-extensions:event-group "L2VPN";
    leaf ip-address {
      type string;
      description
        "IP address that has been suppressed.";
    }
    leaf service-name {
      description
        "Name of L2VPN service";
      type string;
    }
    leaf ip-loop-detection-window-period {
      type uint16 {
        range "1..600";
      }
      description
        "Loop Detection Window Period.";
    }
    leaf ip-move-threshold {
      type uint8 {
        range "2..30";
      }
      description
        "Number of allowed Moves within the Loop Detection Window Period";
    }
  }

  notification IP_MOBILITY_IP_ADDRESS_PERMANENTLY_SUPPRESSED {
    description
      "An IP address has exceeded the number of allowed move events and has been permanently suppressed";
    dn-events-extensions:event-severity-level "Warning";
    dn-events-extensions:event-message-string "The IP {ip-address} received in service {service-name} has been permanently suppressed, having crossed the restore-cycles {restore-cycles} limit.";
    dn-events-extensions:event-corrective-action-string "Check configuration, check for layer-3 network loops";
    dn-events-extensions:event-trigger-component-string "fib-manager";
    dn-events-extensions:event-group "L2VPN";
    leaf ip-address {
      type string;
      description
        "IP address that has been permanently suppressed.";
    }
    leaf service-name {
      description
        "Name of L2VPN service";
      type string;
    }
    leaf restore-cycles {
      type uint8 {
        range "1..10";
      }
      description
        "The number of restore-cycles allowed before permanantly suppressing the IP address.";
    }
  }

  notification IP_MOBILITY_IP_ADDRESS_RELEASED {
    description
      "An IP address that was suppressed has now been released";
    dn-events-extensions:event-severity-level "Info";
    dn-events-extensions:event-message-string "The IP {ip-address} received in service {service-name} that was suppressed, has been released due to {release-reason}.";
    dn-events-extensions:event-corrective-action-string "This is informational, no corrective action required.";
    dn-events-extensions:event-trigger-component-string "fib-manager";
    dn-events-extensions:event-group "L2VPN";
    leaf ip-address {
      type string;
      description
        "IP address that was suppressed.";
    }
    leaf service-name {
      description
        "Name of L2VPN service";
      type string;
    }
    leaf release-reason {
      type string;
      description
        "Release Reason";
    }
  }

  notification L2_MAC_MOBILITY_INTERFACE_SHUTDOWN {
    description
      "An interface has been shut down due to MAC mobility suppression.";
    dn-events-extensions:event-severity-level "Notice";
    dn-events-extensions:event-message-string "The MAC mobility prevention ac-shutdown action is being applied to the interface {interface-name} associated with EVPN service {service-name}, triggered by MAC Address {mac-address}.";
    dn-events-extensions:event-corrective-action-string "Check the configuration for layer-2 network loops and/or MAC Mobility issues.";
    dn-events-extensions:event-trigger-component-string "L2VPN";
    dn-events-extensions:event-group "L2VPN";
    leaf service-name {
      description
        "Name of L2VPN service";
      type string;
    }
    leaf interface-name {
      type string;
      description
        "Interface name";
    }
    leaf mac-address {
      type string;
      description
        "MAC address that triggered shutdown";
    }
  }

  notification L2_MAC_MOBILITY_INTERFACE_PERMANENTLY_SHUTDOWN {
    description
      "An interface has been permanently shut down due to MAC mobility. Too many MAC move related shutdowns occurred within the allowed time period.";
    dn-events-extensions:event-severity-level "Notice";
    dn-events-extensions:event-message-string "The MAC mobility prevention permanent ac-shutdown action is being applied to interface {interface-name} associated with EVPN service {service-name}. Last shutdown triggered by MAC {mac-address}.";
    dn-events-extensions:event-corrective-action-string "Check the configuration for layer-2 network loops and/or MAC Mobility issues.";
    dn-events-extensions:event-trigger-component-string "L2VPN";
    dn-events-extensions:event-group "L2VPN";
    leaf service-name {
      description
        "Name of L2VPN service";
      type string;
    }
    leaf interface-name {
      type string;
      description
        "Interface name";
    }
    leaf mac-address {
      type string;
      description
        "MAC address that triggered shutdown.";
    }
  }

  notification L2_MAC_MOBILITY_INTERFACE_RELEASED {
    description
      "The MAC Mobility Prevention mechanism has released an AC interface from shut down.";
    dn-events-extensions:event-severity-level "Info";
    dn-events-extensions:event-message-string "The MAC Mobility prevention ac-shutdown mechanism applied to Interface {interface-name} associated with EVPN service {service-name}, has been released.";
    dn-events-extensions:event-corrective-action-string "This is informational, no corrective action required.";
    dn-events-extensions:event-trigger-component-string "L2VPN";
    dn-events-extensions:event-group "L2VPN";
    leaf service-name {
      description
        "Name of L2VPN service";
      type string;
    }
    leaf interface-name {
      type string;
      description
        "Interface name";
    }
  }

  notification L2_ETREE_ES_INCONSISTENCY {
    description
      "Inconsistent E-TREE designations configuration has been detected for the same ESI between this PE and a neighbor PE.";
    dn-events-extensions:event-severity-level "Notice";
    dn-events-extensions:event-message-string "The ACs on ES {esi-number} on service {service-name} has been configured inconsistently, as both E-TREE Root and Leaf, between this PE and a neighbor PE.";
    dn-events-extensions:event-corrective-action-string "Check configuration of the ACs of this ESI";
    dn-events-extensions:event-trigger-component-string "BGP";
    dn-events-extensions:event-group "L2VPN";
    leaf esi-number {
      type string;
      description
        "The ESI for which the E-TREE inconsistency has occurred.";
    }
    leaf service-name {
      description
        "Name of L2VPN service";
      type string;
    }
  }

  // L2 Loop Detection

  notification L2_LOOP_DETECTION_INTERFACE_SHUTDOWN {
    description
      "A layer-2 loop has been detected and one or more interfaces have been shutdown.";
    dn-events-extensions:event-severity-level "Warning";
    dn-events-extensions:event-message-string "The local loop prevention ac-shutdown action is being applied to the interface {interface-name} associated with service {service-type} {service-name}, triggered by MAC {mac-address}";
    dn-events-extensions:event-corrective-action-string "Check configuration, check for layer-2 network loops";
    dn-events-extensions:event-trigger-component-string "fib-manager";
    dn-events-extensions:event-group "fib-manager";
    leaf interface-name {
      type string;
      description
        "Name of Interface that has been shutdown";
    }
    leaf service-type {
      description
        "Layer-2 Service Type";
      type enumeration {
        enum BRIDGE_DOMAIN;
        enum EVPN;
      }
    }
    leaf service-name {
      description
        "Name of Layer-2 service";
      type string;
    }
    leaf mac-address {
      type string;
      description
        "MAC address that caused the interface shutdown.";
    }
  }

  notification L2_LOOP_DETECTION_INTERFACE_RELEASED {
    description
      "The interface shutdown due to layer-2 loop detection has been released from the ac-shutdown action.";
    dn-events-extensions:event-severity-level "Info";
    dn-events-extensions:event-message-string "The local loop prevention ac-shutdown action applied to the interface {interface-name} associated with service {service-type} {service-name}, has been released";
    dn-events-extensions:event-corrective-action-string "This is informational, no corrective action required.";
    dn-events-extensions:event-trigger-component-string "fib-manager";
    dn-events-extensions:event-group "fib-manager";
    leaf interface-name {
      type string;
      description
        "Name of Interface that has been shutdown";
    }
    leaf service-type {
      description
        "Layer-2 Service Type";
      type enumeration {
        enum BRIDGE_DOMAIN;
        enum EVPN;
      }
    }
    leaf service-name {
      description
        "Name of Layer-2 service";
      type string;
    }
  }

  notification L2_LOOP_DETECTION_INTERFACE_PERMANENTLY_SHUTDOWN {
    description
      "An interface has been permanently shutdown, as it has had too many MAC move related shutdowns in the time period";
    dn-events-extensions:event-severity-level "Warning";
    dn-events-extensions:event-message-string "The local loop prevention permanent ac-shutdown action is being applied to the interface {interface-name} associated with service {service-type} {service-name}, Last shutdown triggered by MAC {mac-address}";
    dn-events-extensions:event-corrective-action-string "Check configuration, check for layer-2 network loops";
    dn-events-extensions:event-trigger-component-string "fib-manager";
    dn-events-extensions:event-group "fib-manager";
    leaf interface-name {
      type string;
      description
        "Name of Interface that has been permanently shutdown";
    }
    leaf service-type {
      description
        "Layer-2 Service Type";
      type enumeration {
        enum BRIDGE_DOMAIN;
        enum EVPN;
      }
    }
    leaf service-name {
      description
        "Name of Layer-2 service";
      type string;
    }
    leaf mac-address {
      type string;
      description
        "MAC address that caused the last interface shutdown.";
    }
  }

  notification EVPN_MAC_IP_TABLE_THRESHOLD_EXCEEDED {
    description
      "The number of entries in the MAC-IP Table has crossed the 90% threshold of the configured limit for this service instance.";
    dn-events-extensions:event-severity-level "Warning";
    dn-events-extensions:event-message-string "The number of MAC-IP entries for this service instance {service-name} has crossed the 90% threshold of the configured limit {limit}, the current number of entries is {numeric-value}.";
    dn-events-extensions:event-corrective-action-string "No corrective action.";
    dn-events-extensions:event-trigger-component-string "fib-manager";
    dn-events-extensions:event-group "fib-manager";
    leaf service-name {
      type string;
      description
        "The name of the service instance";
    }
    leaf limit {
      type uint32;
      description
        "The configured MAC-IP Table limit";
    }
    leaf numeric-value {
      type uint32;
      description
        "Current number of entries in the MAC-IP Table of this service instance";
    }
  }

  notification EVPN_MAC_IP_TABLE_THRESHOLD_CLEARED {
    description
      "MAC-IP Table entries have been removed, the number of MAC-IP entries is below the 85% threshold of the configured limit for this service instance.";
    dn-events-extensions:event-severity-level "Info";
    dn-events-extensions:event-message-string "The number of MAC-IP entries for this service instance {service-name} has dropped below the 85% threshold of the configured limit {limit}, the current number of entries is {numeric-value}.";
    dn-events-extensions:event-corrective-action-string "This is informational, no corrective action required.";
    dn-events-extensions:event-trigger-component-string "fib-manager";
    dn-events-extensions:event-group "fib-manager";
    leaf service-name {
      type string;
      description
        "The name of the service instance";
    }
    leaf limit {
      type uint32;
      description
        "The configured MAC-IP Table limit";
    }
    leaf numeric-value {
      type uint32;
      description
        "Current number of entries in the MAC-IP Table of this service instance";
    }
  }

  notification TOTAL_EVPN_MAC_IP_TABLE_THRESHOLD_EXCEEDED {
    description
      "The total number of entries in the MAC-IP Table, for all services, has crossed the 90% threshold of the limit.";
    dn-events-extensions:event-severity-level "Warning";
    dn-events-extensions:event-message-string "The total number of MAC-IP entries, for all services, has crossed the 90% threshold of the limit {limit}, the current number of entries is {numeric-value}.";
    dn-events-extensions:event-corrective-action-string "No corrective action.";
    dn-events-extensions:event-trigger-component-string "fib-manager";
    dn-events-extensions:event-group "fib-manager";
    leaf limit {
      type uint32;
      description
        "The Total MAC-IP Table limit";
    }
    leaf numeric-value {
      type uint32;
      description
        "Current total number of entries in the MAC-IP Table for all services";
    }
  }

  notification TOTAL_EVPN_MAC_IP_TABLE_THRESHOLD_CLEARED {
    description
      "MAC-IP Table entries have been removed, the total number of MAC-IP entries is below the 85% threshold of the limit.";
    dn-events-extensions:event-severity-level "Info";
    dn-events-extensions:event-message-string "The total number of MAC-IP entries for all services has dropped below the 85% threshold of the limit {limit}, the current number of entries is {numeric-value}.";
    dn-events-extensions:event-corrective-action-string "This is informational, no corrective action required.";
    dn-events-extensions:event-trigger-component-string "fib-manager";
    dn-events-extensions:event-group "fib-manager";
    leaf limit {
      type uint32;
      description
        "The Total MAC-IP Table limit";
    }
    leaf numeric-value {
      type uint32;
      description
        "Current total number of entries in the MAC-IP Table for all services";
    }
  }

  // TPM and UEFI security events

  notification TPM_PCR_REFERENCE_QUOTE_MISSING {
    description
      "Missing reference TPM PCR quote for measured boot comparison.";
    dn-events-extensions:event-severity-level "Error";
    dn-events-extensions:event-message-string "Missing reference TPM PCR quote on {node-type} {node-id}.";
    dn-events-extensions:event-corrective-action-string "Verify setup and enablement of measured boot support.";
    dn-events-extensions:event-trigger-component-string "Sys info";
    dn-events-extensions:event-group "Platform";
    leaf node-type {
      type string;
      description
        "Node type";
    }
    leaf node-id {
      type string;
      description
        "Node ID";
    }
  }

  notification TPM_PCR_MEASURED_BOOT_QUOTE_MISMATCH_FAILURE {
    description
      "Measured boot TPM PCR quote does not match expected values.";
    dn-events-extensions:event-severity-level "Error";
    dn-events-extensions:event-message-string "Measured boot TPM PCR quote does not match expected values on {node-type} {node-id}.";
    dn-events-extensions:event-corrective-action-string "Verify setup and enablement of measured boot support.";
    dn-events-extensions:event-trigger-component-string "Sys info";
    dn-events-extensions:event-group "Platform";
    leaf node-type {
      type string;
      description
        "Node type";
    }
    leaf node-id {
      type string;
      description
        "Node ID";
    }
  }

  notification TPM_PCR_MEASURED_BOOT_QUOTE_MATCH {
    description
      "Measured boot TPM PCR quote matches expected values.";
    dn-events-extensions:event-severity-level "Info";
    dn-events-extensions:event-message-string "Measured boot TPM PCR quote matches expected values on {node-type} {node-id}.";
    dn-events-extensions:event-corrective-action-string "This is informational, no corrective action required.";
    dn-events-extensions:event-trigger-component-string "Sys info";
    dn-events-extensions:event-group "Platform";
    leaf node-type {
      type string;
      description
        "Node type";
    }
    leaf node-id {
      type string;
      description
        "Node ID";
    }
  }

  notification TPM_PCR_REFERENCE_QUOTE_UPDATED {
    description
      "Reference TPM PCR quote updated.";
    dn-events-extensions:event-severity-level "Notice";
    dn-events-extensions:event-message-string "Reference TPM PCR quote updated on {node-type} {node-id}.";
    dn-events-extensions:event-corrective-action-string "Verify reference quote update is expected as part of initial setup or measured image update.";
    dn-events-extensions:event-trigger-component-string "Sys info";
    dn-events-extensions:event-group "Platform";
    leaf node-type {
      type string;
      description
        "Node type";
    }
    leaf node-id {
      type string;
      description
        "Node ID";
    }
  }

  notification UEFI_DNOS_UPDATE_SIGNATURE_VALIDATION_PASSED {
    description
      "DNOS image signature validation during update based on UEFI secure boot keys has passed.";
    dn-events-extensions:event-severity-level "Info";
    dn-events-extensions:event-message-string "Software image signature validation during DNOS update on {node-type} {node-id} image type {image-type} passed.";
    dn-events-extensions:event-corrective-action-string "This is informational, no corrective action required.";
    dn-events-extensions:event-trigger-component-string "Sys info";
    dn-events-extensions:event-group "Platform";
    leaf node-type {
      type string;
      description
        "Node type";
    }
    leaf node-id {
      type string;
      description
        "Node ID";
    }
    leaf image-type {
      type enumeration {
        enum dnos;
        enum golden-image;
        enum base-os;
      }
    }
  }

  notification UEFI_DNOS_UPDATE_SIGNATURE_VALIDATION_FAILED {
    description
      "DNOS image signature validation during update based on UEFI secure boot keys has failed.";
    dn-events-extensions:event-severity-level "Error";
    dn-events-extensions:event-message-string "Software image signature validation during DNOS update on {node-type} {node-id} image type {image-type} failed.";
    dn-events-extensions:event-corrective-action-string "Verify UEFI secure boot keys are installed.";
    dn-events-extensions:event-trigger-component-string "Sys info";
    dn-events-extensions:event-group "Platform";
    leaf node-type {
      type string;
      description
        "Node type";
    }
    leaf node-id {
      type string;
      description
        "Node ID";
    }
    leaf image-type {
      type enumeration {
        enum dnos;
        enum golden-image;
        enum base-os;
      }
    }
  }

  notification USER_PASSWORD_RESET_TO_DEFAULT {
    description
      "The root password has been reset to the default value.";
    dn-events-extensions:event-severity-level "Notice";
    dn-events-extensions:event-message-string "User {user-name} password has been reset to default on {node-type} {node-id} serial number {serial-number}";
    dn-events-extensions:event-corrective-action-string "Change the root password to a secure, non-default value immediately.";
    dn-events-extensions:event-trigger-component-string "Management";
    dn-events-extensions:event-group "Security";
    leaf user-name {
      type string;
      description
        "User name";
    }
    leaf node-type {
      type string;
      description
        "Node type";
    }
    leaf node-id {
      type string;
      description
        "Node ID";
    }
    leaf serial-number {
      type string;
      description
        "Node serial number";
    }
  }

  notification L2_MAC_MOBILITY_NON_VOLATILE_STORAGE_FULL {
    description
      "Non-volatile storage space for the MAC-Mobility Table is full";
    dn-events-extensions:event-severity-level "Warning";
    dn-events-extensions:event-message-string "The non-volatile storage space for the MAC-Mobility Table is full, in case of process restart or NCC failover, information will be lost.";
    dn-events-extensions:event-corrective-action-string "No corrective action.";
    dn-events-extensions:event-trigger-component-string "RIB";
    dn-events-extensions:event-group "System";
  }

  notification L2_MAC_MOBILITY_NON_VOLATILE_STORAGE_AVAILABLE {
    description
      "Non-volatile storage space forthe MAC-Mobility Table is available";
    dn-events-extensions:event-severity-level "Info";
    dn-events-extensions:event-message-string "Non-volatile storage space is now available for moved MAC entries";
    dn-events-extensions:event-corrective-action-string "This is informational, no corrective action required.";
    dn-events-extensions:event-trigger-component-string "RIB";
    dn-events-extensions:event-group "System";
  }

  notification CLOCK_STATE_CHANGE {
    description
      "The Synchronous Ethernet (SyncE) clock state has changed.";
    dn-events-extensions:event-severity-level "Info";
    dn-events-extensions:event-message-string "{node-type} {node-id} reports a SyncE clock state change from {orig-state} to {new-state}.";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf orig-state {
      description
        "Operating state of the clock before state change";
      type enumeration {
        enum error;
        enum freerun;
        enum holdover;
        enum fastlock;
        enum acquiring;
        enum locked;
      }
    }
    leaf new-state {
      description
        "Operating state of the clock after state change";
      type enumeration {
        enum error;
        enum freerun;
        enum holdover;
        enum fastlock;
        enum acquiring;
        enum locked;
      }
    }
  }

  notification CLOCK_FAILURE {
    description
      "The Synchronous Ethernet (SyncE) clock has lost frequency synchronization from the reference source.";
    dn-events-extensions:event-severity-level "Warning";
    dn-events-extensions:event-message-string "{node-type} {node-id} reports that the SyncE clock entered Holdover state.";
    dn-events-extensions:event-corrective-action-string "Verify synchronization has been restored. Replace the failing reference source if you keep losing synchronization.";
    dn-events-extensions:event-trigger-component-string "WB Agent";
    dn-events-extensions:event-group "clock";
    leaf node-type {
      type string;
      description
        "Node type";
    }
    leaf node-id {
      type string;
      description
        "Node ID";
    }
  }

  notification CLOCK_SOURCE_SWITCH {
    description
      "The Synchronous Ethernet (SyncE) clock has switched to another reference source.";
    dn-events-extensions:event-severity-level "Notice";
    dn-events-extensions:event-message-string "{node-type} {node-id} reports that the SyncE source clock changed from {source-interface-name} to {new_source-interface-name}. Reason: {source-switch-reason}.";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf source-interface-name {
      type string;
      description
        "Source interface name (e.g. ge400-0/0/0, smb-10mhz)";
    }
    leaf new-source-interface-name {
      type string;
      description
        "Source interface name (e.g. ge400-0/0/0, smb-10mhz)";
    }
    leaf source-switch-reason {
      type enumeration {
        enum ql_based;
        enum revertive;
        enum signal_fail;
      }
    }
  }

  notification CLOCK_SYNC_SOURCE_DEGRADED {
    description
      "The Synchronous Ethernet (SyncE) reference source is degraded.";
    dn-events-extensions:event-severity-level "Notice";
    dn-events-extensions:event-message-string "{node-type} {node-id} reports that the SyncE source {source-interface-name} has degraded to QL: {quality-level}. Reason: {source-degrade-reason}.";
    dn-events-extensions:event-corrective-action-string "Consider replacing the degraded reference source.";
    dn-events-extensions:event-trigger-component-string "WB Agent";
    dn-events-extensions:event-group "clock";
    leaf node-type {
      type string;
      description
        "Node type";
    }
    leaf node-id {
      type string;
      description
        "Node ID";
    }
    leaf source-interface-name {
      type string;
      description
        "Source interface name (e.g. ge400-0/0/0, smb-10mhz)";
    }
    leaf quality-level {
      description
        "The quality level as viewed by the G.781 selection process.";
      type enumeration {
        /* option-1 */
        enum ql_prc;
        enum ql_ssu_a;
        enum ql_ssu_b;
        enum ql_sec;
        enum ql_dnu;
        /* option-2 */
        enum ql_prs;
        enum ql_stu;
        enum ql_st2;
        enum ql_tnc;
        enum ql_st3e;
        enum ql_st3;
        enum ql_smc;
        enum ql_prov;
        enum ql_dus;
        /* no quality level */
        enum no_ql;
      }
    }
    leaf source-degrade-reason {
      type enumeration {
        enum QL_degraded;
        enum loss_of_signal;
        enum lockout;
        enum esmc_timeout;
        enum frequency_out_of_range;
        enum link_down;
      }
    }
  }

  notification CLOCK_SYNC_SOURCE_QUALIFIED {
    description
      "The Synchronous Ethernet (SyncE) reference source can be selected as a clock reference source.";
    dn-events-extensions:event-severity-level "Info";
    dn-events-extensions:event-message-string "{node-type} {node-id} reports that the SyncE source {source-interface-name} is qualified as clock reference source.";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf source-interface-name {
      type string;
      description
        "Source interface name (e.g. ge400-0/0/0, smb-10mhz)";
    }
  }

  notification CLOCK_CONFIG_CHANGE {
    description
      "The Synchronous Ethernet (SyncE) clock configuration has changed.";
    dn-events-extensions:event-severity-level "Info";
    dn-events-extensions:event-message-string "{node-type} {node-id} reports that the SyncE clock configuration has changed. "
                                            + "Original configuration: SyncE enable: {orig-admin-state}, QL-enable: {orig-ql-enable}, Synchoronization option: {orig-sync-option}. "
                                            + "New configuration: SyncE enable: {admin-state}, QL-enable: {ql-enable}, Synchoronization option: {sync-option}. ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf orig-admin-state {
      description
        "Original clock configuration global SyncE enable value";
      type enumeration {
        enum disabled;
        enum enabled;
      }
    }
    leaf admin-state {
      description
        "New clock configuration global SyncE enable value";
      type enumeration {
        enum disabled;
        enum enabled;
      }
    }
    leaf orig-ql-enable {
      description
        "Original clock configuration QL-enable value";
      type enumeration {
        enum disabled;
        enum enabled;
      }
    }
    leaf ql-enable {
      description
        "New clock configuration QL-enable value";
      type enumeration {
        enum disabled;
        enum enabled;
      }
    }
    leaf orig-sync-option {
      description
        "Original clock configuration clock synchronization option value";
      type enumeration {
        enum option-1;
        enum option-2;
      }
    }
    leaf sync-option {
      description
        "New clock configuration clock synchronization option value";
      type enumeration {
        enum option-1;
        enum option-2;
      }
    }
  }

  notification CLOCK_SOURCE_CONFIG_CHANGE {
    description
      "The Synchronous Ethernet (SyncE) clock source configuration has changed.";
    dn-events-extensions:event-severity-level "Info";
    dn-events-extensions:event-message-string "{node-type} {node-id} reports that the SyncE source configuration has changed. "
                                            + "Name: {interface-name} "
                                            + "Original configuration: priority: {orig-source-priority}, wtr: {orig-wtr-time}, holdoff {orig-holdoff-time}. "
                                            + "New configuration: priority: {source-priority}, wtr: {wtr-time}, holdoff {holdoff-time}. ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf orig-source-priority {
      description
        "Original clock source priority";
      type uint8 {
        range "0..255";
      }
    }
    leaf source-priority {
      description
        "New clock source priority";
      type uint8 {
        range "0..255";
      }
    }
    leaf interface-name {
      type string;
      description
        "Source interface name (e.g. ge400-0/0/0, smb-10mhz)";
    }
    leaf orig-wtr-time {
      description
        "Original source interface wait-to-restore time";
      type uint8 {
        range "0..12";
      }
    }
    leaf wtr-time {
      description
        "New source interface wait-to-restore time";
      type uint8 {
        range "0..12";
      }
    }
    leaf orig-holdoff-time {
      description
        "Original source interface holdoff time";
      type uint16 {
        range "300..1800";
      }
    }
    leaf holdoff-time {
      description
        "New source interface holdoff time";
      type uint16 {
        range "300..1800";
      }
    }
  }

  notification SYSTEM_PROFILE_CHANGE {
    description
      "System profile change is required.";
    dn-events-extensions:event-severity-level "Info";
    dn-events-extensions:event-message-string "System profile change is required in NCP {ncp-id} from profile {old-profile-name} to profile {new-profile-name}. WB Agent process in NCP {ncp-id} will restart for the change to take effect.";
    dn-events-extensions:event-corrective-action-string "This is informational, no corrective action required.";
    dn-events-extensions:event-trigger-component-string "Element Manager";
    dn-events-extensions:event-group "System";
    leaf ncp-id {
      type uint16;
      description
        "NCP ID";
    }
    leaf old-profile-name {
      type string;
      description
        "The name of the current system profile";
    }
    leaf new-profile-name {
      type string;
      description
        "The name of the candidate system profile";
    }
  }

  notification PTP_CLOCK_CONFIG_CHANGE {
    description
      "The Precision Time Protocol (PTP / IEEE. 1588v2) clock state has changed.";
    dn-events-extensions:event-severity-level "Info";
    dn-events-extensions:event-message-string "{node-type} {node-id} PTP clock state has changed."
                                            + "Profile: {ptp-profile} "
                                            + "Original admin state: {orig-admin-state}, New admin state: {new-admin-state} "
                                            + "Original holdover time: {orig-holdover-time}, New holdover time: {new-holdover-time} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf ptp-profile {
      type string;
      description
        "PTP profile";
    }
    leaf orig-admin-state {
      description
        "Original PTP admin state";
      type enumeration {
        enum disabled;
        enum enabled;
      }
    }
    leaf new-admin-state {
      description
        "New PTP admin state";
      type enumeration {
        enum disabled;
        enum enabled;
      }
    }
    leaf orig-holdover-time {
      description
        "PTP clock holdover time";
      type uint16;
    }
    leaf new-holdover-time {
      description
        "PTP clock holdover time";
      type uint16;
    }
  }

  notification PTP_PORT_STATE_CHANGE {
    description
      "The Precision Time Protocol (PTP / IEEE. 1588v2) clock port state has changed.";
    dn-events-extensions:event-severity-level "Info";
    dn-events-extensions:event-message-string "{node-type} {node-id} PTP clock port state has changed. "
                                            + "Interface: {interface-name} "
                                            + "Profile: {ptp-profile} "
                                            + "Original state: {orig-port-state} "
                                            + "New state: {new-port-state} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf interface-name {
      type string;
      description
        "Source interface name (e.g. ge400-0/0/0)";
    }
    leaf ptp-profile {
      type string;
      description
        "PTP profile";
    }
    leaf orig-port-state {
      description
        "Original PTP port state";
      type enumeration {
        enum unknown;
        enum initializing;
        enum faulty;
        enum disabled;
        enum listening;
        enum pre-master;
        enum master;
        enum passive;
        enum uncalibrated;
        enum slave;
      }
    }
    leaf new-port-state {
      description
        "New PTP port state";
      type enumeration {
        enum unknown;
        enum initializing;
        enum faulty;
        enum disabled;
        enum listening;
        enum pre-master;
        enum master;
        enum passive;
        enum uncalibrated;
        enum slave;
      }
    }
  }

  notification PTP_RECV_MSG_RATE_DROP {
    description
      "The Precision Time Protocol (PTP / IEEE. 1588v2) incomming receive message rate has dropped below 50% of the expected rate on the port.";
    dn-events-extensions:event-severity-level "Warning";
    dn-events-extensions:event-message-string "{node-type} {node-id} PTP clock port's received message rate has dropped. "
                                            + "Interface: {interface-name} "
                                            + "Message type: {msg-type} "
                                            + "Received in period: {received-in-period} "
                                            + "Expected in period: {expected-in-period} "
                                            + "Time period in seconds: {time-period} ";
    dn-events-extensions:event-corrective-action-string "Check the port connectivity and the clock configuration connected to the port.";
    dn-events-extensions:event-trigger-component-string "WB Agent";
    dn-events-extensions:event-group "clock";
    leaf node-type {
      type string;
      description
        "Node type";
    }
    leaf node-id {
      type string;
      description
        "Node ID";
    }
    leaf interface-name {
      type string;
      description
        "Source interface name (e.g. ge400-0/0/0)";
    }
    leaf msg-type {
      description
        "PTP message type";
      type enumeration {
        enum sync {
          value 0;
        }
        enum delay_req {
          value 1;
        }
        enum follow_up {
          value 8;
        }
        enum delay_resp {
          value 9;
        }
        enum announce {
          value 11;
        }
        enum management {
          value 13;
        }
      }
    }
    leaf received-in-period {
      type uint32;
      description
        "Number of messages received during measure period.";
    }
    leaf expected-in-period {
      type uint32;
      description
        "Number of messages expected during measure period.";
    }
    leaf time-period {
      type uint32;
      description
        "Period of time in seconds for message count measurement.";
    }
  }

  notification PTP_CLOCK_PARENT_CHANGE {
    description
      "The Precision Time Protocol (PTP / IEEE. 1588v2) clock parent has changed.";
    dn-events-extensions:event-severity-level "Notice";
    dn-events-extensions:event-message-string "{node-type} {node-id} PTP clock parent has changed. "
                                            + "Original parent: interface {orig-interface-name}, Parent clock identity {orig-parent-identity}, GM identity {orig-gm-identity} "
                                            + "New parent: interface {new-interface-name}, Parent clock identity {new-parent-identity}, GM identity {new-gm-identity} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf orig-interface-name {
      type string;
      description
        "Source interface name (e.g. ge400-0/0/0)";
    }
    leaf orig-parent-identity {
      type string {
        length "1..32";
      }
      description
        "PTP parent clock identity";
    }
    leaf orig-gm-identity {
      type string {
        length "1..32";
      }
      description
        "PTP GM clock idetity";
    }
    leaf new-interface-name {
      type string;
      description
        "Source interface name (e.g. ge400-0/0/0)";
    }
    leaf new-parent-identity {
      type string {
        length "1..32";
      }
      description
        "PTP clock identity";
    }
    leaf new-gm-identity {
      type string {
        length "1..32";
      }
      description
        "PTP GM clock idetity";
    }
  }

  notification PTP_PORT_NON_STANDARD_MSG {
    description
      "The Precision Time Protocol (PTP / IEEE. 1588v2) received a non-standard message.";
    dn-events-extensions:event-severity-level "Warning";
    dn-events-extensions:event-message-string "{node-type} {node-id} PTP clock port received a non-standard message. "
                                            + "Interface: {interface-name} "
                                            + "Receiving port's connected clock identity: {clock-identity} ";
    dn-events-extensions:event-corrective-action-string "Check the clock configuration connected to port.";
    dn-events-extensions:event-trigger-component-string "WB Agent";
    dn-events-extensions:event-group "clock";
    leaf node-type {
      type string;
      description
        "Node type";
    }
    leaf node-id {
      type string;
      description
        "Node ID";
    }
    leaf interface-name {
      type string;
      description
        "Source interface name (e.g. ge400-0/0/0)";
    }
    leaf clock-identity {
      type string {
        length "1..32";
      }
      description
        "PTP clock identity of clock connected to the reporting port";
    }
  }

  notification PTP_PORT_LEAP_SECONDS_CHANGE {
    description
      "The Precision Time Protocol (PTP / IEEE. 1588v2) clock leap59 or leap61 time properties have changed on the port.";
    dn-events-extensions:event-severity-level "Notice";
    dn-events-extensions:event-message-string "{node-type} {node-id} leap59 or leap61 time properties changed on the PTP clock port. "
                                            + "Interface: {interface-name} "
                                            + "Original Leap59 value: {orig-leap59}, New Leap59 value: {new-leap59} "
                                            + "Original Leap61 value: {orig-leap61}, New Leap61 value: {new-leap61} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf interface-name {
      type string;
      description
        "Source interface name (e.g. ge400-0/0/0)";
    }
    leaf orig-leap59 {
      description
        "PTP clock previous Leap59 flag value. Set to true if the last minute of the current UTC day
         contains 59 seconds. Otherwise, it is false";
      type string;
    }
    leaf new-leap59 {
      description
        "PTP clock new Leap59 flag value. Set to true if the last minute of the current UTC day
         contains 59 seconds. Otherwise, it is false";
      type string;
    }
    leaf orig-leap61 {
      description
        "PTP clock previous Leap61 flag value. Set to true if the last minute of the current UTC day
         contains 61 seconds. Otherwise, it is false";
      type string;
    }
    leaf new-leap61 {
      description
        "PTP clock new Leap61 flag value. Set to true if the last minute of the current UTC day
         contains 61 seconds. Otherwise, it is false";
      type string;
    }
  }

  notification PTP_CLOCK_UTC_OFFSET_CHANGE {
    description
      "The Precision Time Protocol (PTP / IEEE. 1588v2) clock time UTC offset properties have changed.";
    dn-events-extensions:event-severity-level "Notice";
    dn-events-extensions:event-message-string "{node-type} {node-id} UTC offset time property has changed. "
                                            + "Original: UTC offset {orig-utc-offset}, UTC offset valid flag {orig-utc-offset-valid} "
                                            + "New: UTC offset {new-utc-offset}, UTC offset valid flag {new-utc-offset-valid} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf orig-utc-offset {
      type int32;
      description
        "Offset between TAI and UTC in seconds";
    }
    leaf new-utc-offset {
      type int32;
      description
        "Offset between TAI and UTC in seconds";
    }
    leaf orig-utc-offset-valid {
      type string;
      description
        "Flag set to True when UTC offset is known to be correct.";
    }
    leaf new-utc-offset-valid {
      type string;
      description
        "Flag set to True when UTC offset is known to be correct.";
    }
  }

  notification PTP_PORT_STEPS_REMOVED_VIOLATION {
    description
      "The Precision Time Protocol (PTP / IEEE. 1588v2) clock received an announce message that exceeded the local steps-removed value.";
    dn-events-extensions:event-severity-level "Warning";
    dn-events-extensions:event-message-string "{node-type} {node-id} PTP clock received an announce message with steps-removed value exceeding local steps-removed limit. "
                                            + "Message received on interface: {interface-name} "
                                            + "Message origin clock identity: {clock-identity} "
                                            + "Announce message steps-removed: {announce-steps-removed} "
                                            + "Configured local steps-removed limit: {local-max-steps-removed} ";
    dn-events-extensions:event-corrective-action-string "Check the local max-steps-removed configuration and network connectivity scheme.";
    dn-events-extensions:event-trigger-component-string "WB Agent";
    dn-events-extensions:event-group "clock";
    leaf node-type {
      type string;
      description
        "Node type";
    }
    leaf node-id {
      type string;
      description
        "Node ID";
    }
    leaf interface-name {
      type string;
      description
        "Source interface name (e.g. ge400-0/0/0)";
    }
    leaf clock-identity {
      type string {
        length "1..32";
      }
      description
        "PTP clock idetity of clock connected to the reporting port";
    }
    leaf announce-steps-removed {
      type uint8;
      description
        "Announce message steps-removed attribute";
    }
    leaf local-max-steps-removed {
      type uint8;
      description
        "Announce message steps-removed qualification limit";
    }
  }

  notification PTP_PORT_DISQUALIFIED {
    description
      "The Precision Time Protocol (PTP / IEEE. 1588v2) clock previously qualified port has been disqualified from taking part in the BMCA.";
    dn-events-extensions:event-severity-level "Notice";
    dn-events-extensions:event-message-string "{node-type} {node-id} port stream has been disqualified from taking part in the BMCA. "
                                            + "Interface: {interface-name} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf interface-name {
      type string;
      description
        "Source interface name (e.g. ge400-0/0/0)";
    }
  }

  notification PTP_PORT_CONFIG_CHANGE {
    description
      "The Precision Time Protocol (PTP / IEEE. 1588v2) clock port configuration has changed.";
    dn-events-extensions:event-severity-level "Info";
    dn-events-extensions:event-message-string "{node-type} {node-id} PTP clock port configuration has changed. "
                                            + "Interface: {interface-name} "
                                            + "Profile: {ptp-profile} "
                                            + "Master-only: {new-master-only} "
                                            + "Local priority: {new-local-priority} "
                                            + "Announce receipt timeout: {new-announce-receipt-timeout} "
                                            + "Multicast address: {new-multicast-addr} "
                                            + "Port delay: {new-port-delay} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf interface-name {
      type string;
      description
        "Source interface name (e.g. ge400-0/0/0)";
    }
    leaf ptp-profile {
      type string;
      description
        "PTP profile";
    }
    leaf new-master-only {
      description
        "PTP port Master-only flag value";
      type string;
    }
    leaf new-local-priority {
      description
        "PTP port Local priority value";
      type uint8;
    }
    leaf new-announce-receipt-timeout {
      description
        "PTP port Announce message receipt timeout value";
      type uint8;
    }
    leaf new-multicast-addr {
      description
        "PTP port Announce message receipt timeout value";
      type enumeration {
        enum non-forwardable;
        enum forwardable;
      }
    }
    leaf new-port-delay {
      description
        "PTP port delay value";
      type int32;
    }
  }

  notification PTP_PTSF_EVENT {
    description
      "The Precision Time Protocol (PTP / IEEE. 1588v2) clock Packet Timing Signal Fail (PTSF) flag has changed.";
    dn-events-extensions:event-severity-level "Info";
    dn-events-extensions:event-message-string "{node-type} {node-id} Packet Timing Signal Fail (PTSF) event has occured. "
                                            + "PTSF event type: {ptsf-type} ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf ptsf-type {
      description
        "PTP packet timing signal fail event type";
      type enumeration {
        enum misc_user;
        enum misc_ql_too_low;
        enum misc_los_from_phy;
        enum misc_wait_to_restore_active;
        enum contract_retry_attempts_fail;
        enum contract_announce_rejected;
        enum contract_sync_rejected;
        enum contract_delay_resp_rejected;
        enum contract_peer_delay_resp_rejected;
        enum contract_announce_rate_too_low;
        enum contract_sync_rate_too_low;
        enum contract_delay_resp_rate_too_low;
        enum contract_peer_delay_resp_rate_too_low;
        enum timeout_loss_announce;
        enum timeout_loss_sync;
        enum timeout_loss_follow_up;
        enum timeout_loss_sync_or_follow_up;
        enum timeout_loss_delay_resp;
        enum timeout_loss_peer_delay_resp;
        enum timeout_loss_peer_delay_folow_up;
        enum unusable_packet_reject_reset;
        enum unusable_loss_timestamps;
        enum unusable_local_time_inacc_exceeded;
        enum unusable_network_time_inacc_exceeded;
        enum freq_pull_in_range_oor;
        enum freq_pdv_freq_metric_fail;
        enum freq_freq_var_too_high;
        enum freq_no_freq_lock;
        enum phase_pdv_phase_metric_fail;
        enum phase_phase_var_too_high;
        enum phase_no_phase_lock;
        enum misc;
        enum contract;
        enum timeout;
        enum unusable;
        enum frequency;
        enum phase;
        enum main;
        enum as_capable_peer_delay_multi_resp;
        enum as_capable_peer_delay_above_threshold;
        enum as_capable_peer_delay_allowed_lost_response;
        enum as_capable;
        enum as_capable_peer_delay_ratio_invalid;
        enum unknown;
      }
    }
  }

  notification PTP_DEFAULT_DATASET_CONFIG_CHANGE {
    description
      "The Precision Time Protocol (PTP / IEEE. 1588v2) clock default dataset configuration has changed.";
    dn-events-extensions:event-severity-level "Info";
    dn-events-extensions:event-message-string "{node-type} {node-id} PTP default dataset configuration has changed "
                                            + "Profile: {ptp-profile} "
                                            + "New configuration: clock type: {new-clock-type}, priority2: {new-priority2}, local priority: {new-local-priority}, max-steps-removed {new-max-steps}, id {new-id}. ";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf ptp-profile {
      type string;
      description
        "PTP profile";
    }
    leaf new-clock-type {
      description
        "PTP clock type";
      type enumeration {
        enum t-gm {
          value 1;
        }
        enum t-bc {
          value 2;
        }
        enum t-tsc {
          value 3;
        }
      }
    }
    leaf new-priority2 {
      description
        "PTP clock priority2 value";
      type uint8;
    }
    leaf new-local-priority {
      description
        "PTP clock local priority value";
      type uint8;
    }
    leaf new-max-steps {
      description
        "PTP clock max steps removed value";
      type uint8;
    }
    leaf new-id {
      type string {
        length "1..32";
      }
      description
        "PTP clock identity";
    }
  }

  notification PTP_GNSS_CONFIG_CHANGE {
    description
      "Precision Time Protocol (PTP / IEEE. 1588v2) clock GNSS configuration has changed.";
    dn-events-extensions:event-severity-level "Info";
    dn-events-extensions:event-message-string "NCP {ncp-id} reports that the PTP clock GNSS configuration has changed. "
                                            + "Previous state: {state}, New state {new-state} "
                                            + "New constellations: : GPS {new-gps}, SBAS {new-sbas}, GALILEO {new-galileo}, BEIDOU {new-beidou}, IMES {new-imes}, QZSS {new-qzss}, GLONASS {new-glonass} "
                                            + "Min. Satellite {min-satellites}, New Min. Satellite {new-min-satellites} "
                                            + "CNO {cno}, New CNO {new-cno} ";
    dn-events-extensions:event-corrective-action-string "This is informational, no corrective action required.";
    dn-events-extensions:event-trigger-component-string "WB Agent";
    dn-events-extensions:event-group "clock";
    leaf ncp-id {
      type uint8;
      description
        "NCP id";
    }
    leaf state {
      type string;
      description
        "GNSS SMA input port state";
    }
    leaf new-state {
      type string;
      description
        "GNSS SMA input port new state";
    }
    leaf new-gps {
      type enumeration {
        enum disabled;
        enum enabled;
      }
      description
        "Enable or disable the Global Positioning System constellation";
    }
    leaf new-sbas {
      type enumeration {
        enum disabled;
        enum enabled;
      }
      description
        "Enable or disable the Satellite-based Augmentation Systems";
    }
    leaf new-galileo {
      type enumeration {
        enum disabled;
        enum enabled;
      }
      description
        "Enable or disable the Galileo (EU) constellation";
    }
    leaf new-beidou {
      type enumeration {
        enum disabled;
        enum enabled;
      }
      description
        "Enable or disable the BeiDou constellation";
    }
    leaf new-imes {
      type enumeration {
        enum disabled;
        enum enabled;
      }
      description
        "Enable or disable Indoor Messaging System";
    }
    leaf new-qzss {
      description
        "Enable or disable the Quasi-Zenith Satellite System (Japan) constellation";
      type enumeration {
        enum disabled;
        enum enabled;
      }
    }
    leaf new-glonass {
      type enumeration {
        enum disabled;
        enum enabled;
      }
      description
        "Enable or disable the Global Navigation Satellite System (Russia) constellation";
    }
    leaf min-satellites {
      type uint8;
      description
        "GNSS navigation minimal number of satellites";
    }
    leaf new-min-satellites {
      type uint8;
      description
        "GNSS navigation minimal number of satellites";
    }
    leaf cno {
      type uint16;
      description
        "GNSS CNO - ratio of the carrier power C to the noise power density N0, expressed in dB-Hz";
    }
    leaf new-cno {
      type uint16;
      description
        "GNSS CNO - ratio of the carrier power C to the noise power density N0, expressed in dB-Hz";
    }
  }

  notification PTP_EXTERNAL_TOD_LOCK_STATE_CHANGE {
    description
      "The Precision Time Protocol (PTP / IEEE. 1588v2) clock external Time of Day source port lock state has changed.";
    dn-events-extensions:event-severity-level "Notice";
    dn-events-extensions:event-message-string "{node-type} {node-id} external ToD {port-type} port lock state: {lock-state}";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf port-type {
      type enumeration {
        enum rj45;
        enum gnss;
      }
      description
        "External ToD port type";
    }
    leaf lock-state {
      type enumeration {
        enum locked;
        enum unlocked;
      }
      description
        "External ToD port lock state";
    }
  }

  notification PTP_EXTERNAL_TOD_SOURCE_FAILURE {
    description
      "The Precision Time Protocol (PTP / IEEE. 1588v2) clock external Time of Day source port failure reported.";
    dn-events-extensions:event-severity-level "Warning";
    dn-events-extensions:event-message-string "{node-type} {node-id} external ToD {port-type} port failure type: {failure-type}";
    dn-events-extensions:event-corrective-action-string "This is informational, no corrective action required.";
    dn-events-extensions:event-trigger-component-string "WB Agent";
    dn-events-extensions:event-group "clock";
    leaf node-type {
      type string;
      description
        "Node type";
    }
    leaf node-id {
      type string;
      description
        "Node ID";
    }
    leaf port-type {
      type enumeration {
        enum rj45;
        enum gnss;
      }
      description
        "External ToD port type";
    }
    leaf failure-type {
      type enumeration {
        enum crc_error {
          value 2;
        }
        enum crc_overflow {
          value 5;
        }
      }
      description
        "External ToD port faliure type";
    }
  }

  notification OSPF_ADVERTISE_MAX_METRIC_ON {
    description
      "OSPF has set the max metric on some metric(s) (IGP/TE/delay). This means other routers will consider the router to be least preferred in some path calculations.";
    dn-events-extensions:event-severity-level "Notice";
    dn-events-extensions:event-message-string "OSPF instance {instance} advertise max-metric was set to on, period: {period}";
    dn-events-extensions:event-corrective-action-string "No corrective action.";
    dn-events-extensions:event-trigger-component-string "ospf";
    dn-events-extensions:event-group "OSPF";
    leaf instance {
      type string;
      description
        "OSPF instance name";
    }
    leaf period {
      type string;
      description
        "The period for which max-metric is set";
    }
  }

  notification OSPF_ADVERTISE_MAX_METRIC_OFF {
    description
      "OSPF has turned off the max metric.";
    dn-events-extensions:event-severity-level "Info";
    dn-events-extensions:event-message-string "OSPF instance {instance} advertise max-metric was set to off";
    dn-events-extensions:event-corrective-action-string "No corrective action.";
    dn-events-extensions:event-trigger-component-string "ospf";
    dn-events-extensions:event-group "OSPF";
    leaf instance {
      type string;
      description
        "OSPF instance name";
    }
  }

  // Access-lists events

  notification ACCESS_LIST_LOG {
    description
      "The packet matched an access-list rule on the indicated interface.";
    dn-events-extensions:event-severity-level "Info";
    dn-events-extensions:event-message-string "A packet from {source-address-and-port}, to {destination-address-and-port} on protocol {protocol} was received on interface {ingress-interface} of VRF {vrf-name} and {forwarding-action}";
    dn-events-extensions:event-corrective-action-string "No corrective action.";
    dn-events-extensions:event-trigger-component-string "WB";
    dn-events-extensions:event-group "ACL";
    leaf source-address-and-port {
      type string;
      description
        "The source IP address and port of the received packet";
    }
    leaf destination-address-and-port {
      type string;
      description
        "The destination IP address and port  of the received packet";
    }
    leaf protocol {
      type string;
      description
        "The protocol of the received packet";
    }
    leaf vrf-name {
      type string;
      description
        "The vrf name the packet was received on";
    }
    leaf forwarding-action {
      type enumeration {
        enum allowed;
        enum denied;
        enum sent-to-cpu;
      }
      description
        "Action being taken on the received packet";
    }
    leaf ingress-interface {
      type string;
      description
        "The ingress interface name the packet was received on";
    }
  }

  notification NCC_REPOSITORY_SYNC_FAILED {
    description
      "The NCCs' repository has failed to be synced.";
    dn-events-extensions:event-severity-level "Warning";
    dn-events-extensions:event-message-string "NCC {node-id} reports that the NCC {remote-node-id} has failed to sync its repository.";
    dn-events-extensions:event-corrective-action-string "This is informational, no corrective action required.";
    dn-events-extensions:event-trigger-component-string "Cluster Manager";
    dn-events-extensions:event-group "System";
    leaf node-id {
      type string;
      description
        "Node ID";
    }
    leaf remote-node-id {
      type string;
      description
        "Remote Node ID";
    }
  }

  notification NCC_REPOSITORY_SYNC_SUCCEEDED {
    description
      "The Synchronous Ethernet (SyncE) reference source can be selected as a clock reference source.";
    dn-events-extensions:event-severity-level "Info";
    dn-events-extensions:event-message-string "NCC {node-id} reports that the NCC {remote-node-id} has completed to sync its repository.";
    dn-events-extensions:event-corrective-action-string "This is informational, no corrective action required.";
    dn-events-extensions:event-trigger-component-string "Cluster Manager";
    dn-events-extensions:event-group "System";
    leaf node-id {
      type string;
      description
        "Node ID";
    }
    leaf remote-node-id {
      type string;
      description
        "Remote Node ID";
    }
  }
}
