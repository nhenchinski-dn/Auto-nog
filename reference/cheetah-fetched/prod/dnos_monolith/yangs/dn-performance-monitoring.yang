module dn-performance-monitoring {
  namespace "http://drivenets.com/ns/yang/dn-performance-monitoring";
  prefix dn-pm;

  import dn-top {
    prefix dn-top;
  }
  import dn-services {
    prefix dn-services;
  }
  import dn-interfaces {
    prefix dn-if;
  }
  import dn-network-services {
    prefix dn-network-services;
  }
  import dn-vrf {
    prefix dn-vrf;
  }
  import ietf-inet-types {
    prefix inet;
  }
  import iana-if-type {
    prefix ianaift;
  }
  import ietf-yang-types {
    prefix yang;
  }
  import dn-group {
    prefix dn-group;
  }

  organization
    "DRIVENETS LTD";
  contact
    "DRIVENETS Customer Service <mailto:support@drivenets.com>";
  description
    "This module contains a collection of YANG definitions for
     managing DRIVENETS performance monitoring.";

  revision 2025-08-10 {
    description
      "Added support for proactive CFM performance monitoring tests";
  }
  revision 2025-07-13 {
    description
      "Added support for CFM performance monitoring tests";
  }
  revision 2025-05-03 {
    description
      "Added apply-groups statement";
  }
  revision 2024-11-19 {
    description
      "Added range to total-loss and successive-loss";
  }
  revision 2024-03-27 {
    description
      "Added support for ICMP echo IP performance measurement";
  }
  revision 2022-09-04 {
    description
      "Added support for simple TWAMP and dynamic link delay measurement";
  }
  revision 2021-11-07 {
    description
      "Initial revision";
  }

  // Typedef statements

  typedef admin-state {
    type enumeration {
      enum enabled;
      enum disabled;
    }
  }

  typedef session-dscp-mode {
    type enumeration {
      enum copy-received-value {
        description
          "Use DSCP value copied from received
           STAMP test packet of the test session.";
      }
      enum use-configured-value {
        description
          "Use DSCP value configured for this
           test session on the Session-Reflector.";
      }
    }
    description
      "DSCP handling mode by Session-Reflector.";
  }

  typedef padding-fill-mode {
    type enumeration {
      enum zero {
        description
          "TWAMP-Test packets are padded with all zeros.";
      }
      enum random {
        description
          "TWAMP-Test packets are padded with pseudo-random
           numbers.";
      }
    }
    description
      "Indicates what type of packet padding is used in the
       TWAMP-Test packets.";
  }

  typedef test-session-state {
    type enumeration {
      enum accepted {
        value 0;
        description
          "Indicates an accepted TWAMP-Test session request.";
      }
      enum failed {
        value 1;
        description
          "Indicates a TWAMP-Test session failure due to
           some unspecified reason (catch-all).";
      }
      enum internal-error {
        value 2;
        description
          "Indicates a TWAMP-Test session failure due to
           an internal error.";
      }
      enum not-supported {
        value 3;
        description
          "Indicates a TWAMP-Test session failure because
           some aspect of the TWAMP-Test session request
           is not supported.";
      }
      enum permanent-resource-limit {
        value 4;
        description
          "Indicates a TWAMP-Test session failure due to
           permanent resource limitations.";
      }
      enum temp-resource-limit {
        value 5;
        description
          "Indicates a TWAMP-Test session failure due to
           temporary resource limitations.";
      }
    }
    description
      "Indicates the Control-Client TWAMP-Test session state.";
  }

  typedef sender-session-state {
    type enumeration {
      enum active {
        description
          "Indicates that the TWAMP-Test session is active.";
      }
      enum failure {
        description
          "Indicates that the TWAMP-Test session has failed.";
      }
    }
    description
      "Indicates the Session-Sender TWAMP-Test session state.";
  }

  typedef percentage {
    type decimal64 {
      fraction-digits 5;
    }
    description
      "Percentage";
  }

  typedef percentile {
    type decimal64 {
      fraction-digits 2;
    }
    description
      "Percentile is a measure used in statistics
       indicating the value below which a given
       percentage of observations in a group of
       observations fall.";
  }

  typedef icmp-echo-session-ref {
    type leafref {
      path "/dn-top:drivenets-top/dn-services:services/dn-pm:performance-monitoring/dn-pm:icmp-echo-sessions/dn-pm:test-session/dn-pm:session-name";
    }
    description
      "Reusable type for by-name reference to a performance-monitoring icmp-echo session.";
  }

  // Grouping statements

  grouping performance-monitoring-config {
    description
      "Top-level grouping for performance monitoring";
    leaf interface-name {
      type dn-if:base-interface-ref;
      must "(/dn-top:drivenets-top/dn-if:interfaces/dn-if:interface[dn-if:name = current()]/dn-if:config-items/dn-if:type = 'ianaift:ethernetCsmacd') or"
         + "(/dn-top:drivenets-top/dn-if:interfaces/dn-if:interface[dn-if:name = current()]/dn-if:config-items/dn-if:type = 'ianaift:ieee8023adLag') or"
         + "(/dn-top:drivenets-top/dn-if:interfaces/dn-if:interface[dn-if:name = current()]/dn-if:config-items/dn-if:type = 'ianaift:l2vlan')" {
        error-message "interface cannot be type of loopback or of type GRE Tunnel";
      }
    }
    container delay-measurement {
      description
        "Delay Measurement configurations";
      leaf static-delay {
        description
          "The Interface Delay in microseconds";
        type uint32 {
          range "1..16777215";
        }
        units "microseconds";
      }
      container link-delay-measurement {
        description
          "Contains Link Delay Measurement configurations";
        leaf admin-state {
          type admin-state;
          default "disabled";
        }
        leaf destination-address {
          description
            "The destination address for dynamic link delay monitoring session.";
          type inet:ip-address;
        }
        leaf profile {
          type leafref {
            path "../../../../../../profiles/link-delay-measurement-profiles/profile/profile-name";
          }
          default "default";
          description
            "The Simple TWAMP link-performance profile containing session parameters configuration";
        }
      }
    }
  }

  grouping stamp-link-performance-profile-config {
    description
      "Configuration items for STAMP profile";
    leaf profile-name {
      description
        "The name of the profile.";
      type string {
        length "1..255";
        pattern '[a-zA-Z0-9_-]+';
      }
    }
    /*        leaf dscp-handling-mode {
    type session-dscp-mode;
    default copy-received-value;
    description
    "Session-Reflector handling of DSCP:
    	- use value copied from received TWAMP-Test packet;
    	- use value explicitly configured";
    } */
    leaf dscp-value {
      description
        "The DSCP value for reflected STAMP packets if dscp-handling-mode is set to use-configured-value.";
      type inet:dscp {
        range "0..56";
      }
      default "56";
    }
    leaf packet-padding-mode {
      type padding-fill-mode;
      default "zero";
      description
        "The packet padding mode";
    }
    leaf packet-padding-size {
      type uint32 {
        range "60..1400";
      }
      default "60";
      description
        "Size of the Packet Padding. Suggested to run
         Path MTU Discovery to avoid packet fragmentation
         in IPv4 and packet backholing in IPv6";
    }
    leaf probe-interval {
      description
        "The interval between subsequent probes.";
      type uint8 {
        range "1..255";
      }
      units "seconds";
      default "3";
    }
    leaf computation-interval {
      description
        "Periodic computation interval.";
      type uint16 {
        range "1..3600";
      }
      units "seconds";
      default "30";
    }
    container advertisement {
      description
        "Contains advertisement configuration";
      container periodic {
        description
          "Contains periodic advertisement configuration";
        leaf interval {
          description
            "The interval between subsequent advertisements.";
          type uint16 {
            range "30..3600";
          }
          units "seconds";
          default "120";
        }
        choice delay-change-threshold {
          description
            "The minimal delay change to trigger periodic advertisement.";
          default "percentages";
          case percentages {
            description
              "The minimal delay change in percentages";
            leaf minimum-change-percentages {
              type uint8 {
                range "5..100";
              }
              units "percentages";
              default "10";
            }
          }
          case microseconds {
            description
              "The minimal delay change in microseconds";
            leaf minimum-change-microseconds {
              type uint32 {
                range "1..100000";
              }
              units "microseconds";
              default "1000";
            }
          }
        }
      }
      container accelerated {
        description
          "Contains accelerated advertisement configuration";
        leaf admin-state {
          type admin-state;
          default "disabled";
        }
        choice delay-change-threshold {
          description
            "The minimal delay change to trigger accelerated advertisement.";
          default "percentages";
          case percentages {
            description
              "The minimal delay change in percentages";
            leaf minimum-change-percentages {
              type uint8 {
                range "5..100";
              }
              units "percentages";
              default "20";
            }
          }
          case microseconds {
            description
              "The minimal delay change in microseconds";
            leaf minimum-change-microseconds {
              type uint32 {
                range "1..100000";
              }
              units "microseconds";
              default "1000";
            }
          }
        }
      }
    }
  }

  grouping stamp-session-parameters {
    description
      "Parameters common among
       Session-Sender and Session-Reflector";
    leaf source-ip {
      type inet:ip-address;
      mandatory true;
      description
        "Sender IP address";
    }
    /*	leaf sender-udp-port {
    		type inet:port-number {
    			range "49152..65535";
    		}
    		mandatory true;
    		description 
    			"Sender UDP port number";
    	} */
    leaf destination-ip {
      type inet:ip-address;
      mandatory true;
      description
        "Reflector IP address";
    }
    leaf destination-vrf {
      type leafref {
        path "/dn-top:drivenets-top/dn-network-services:network-services/dn-vrf:vrfs/dn-vrf:vrf/dn-vrf:vrf-name";
      }
      default "default";
      must "((current() != 'mgmt0') and (current() != 'mgmt-ncc-0') and (current() != 'mgmt-ncc-1'))";
      description
        "Reflector VRF";
    }
    /*		leaf destination-udp-port {
    type inet:port-number{
    range "49152..65535";
    }
    mandatory true;
    description 
    "Reflector UDP port number";
    } */
  }

  grouping maintenance-statistics {
    description
      "Maintenance statistics grouping";
    leaf sent-packets {
      type uint32;
      description
        "Packets sent";
    }
    leaf rcv-packets {
      type uint32;
      description
        "Packets received";
    }
    /* leaf sent-packets-error {
    	type uint32;
    	description
    		"Packets sent error";
    }
    
    leaf rcv-packets-error {
    	type uint32;
    	description
    		"Packets received error";
    }
    
    leaf duplicate-packets  {
    	type uint32;
    	description
    		"Duplicate packets";
    }
    leaf reordered-packets  {
    	type uint32;
    	description
    		"Reordered packets";
    }
    leaf loss-packets  {
    	type uint32;
    	description
    		"Loss packets";
    }
    
    leaf last-sent-seq {
    	type uint32;
    	description
    		"Last sent sequence number";
    }
    
    leaf last-rcv-seq {
    	type uint32;
    	description
    		"Last received sequence number";
    } */
  }

  grouping icmp-echo-maintenance-statistics {
    description
      "Maintenance statistics grouping";
    leaf sent-packets {
      type uint32;
      description
        "Packets sent";
    }
    leaf rcv-packets {
      type uint32;
      description
        "Packets received";
    }
    /* leaf sent-packets-error {
    	type uint32;
    	description
    		"Packets sent error";
    } */
    leaf rcv-packets-error {
      type uint32;
      description
        "Packets received error";
    }
    leaf duplicate-packets {
      type uint32;
      description
        "Duplicate packets";
    }
    /* leaf reordered-packets  {
    	type uint32;
    	description
    		"Reordered packets";
    } */
    /* leaf loss-packets  {
    	type uint32;
    	description
    		"Loss packets";
    } */
    leaf last-sent-seq {
      type uint32;
      description
        "Last sent sequence number";
    }
    leaf last-rcv-seq {
      type uint32;
      description
        "Last received sequence number";
    }
  }

  grouping delay-statistics {
    description
      "Delay statistics grouping";
    container delay {
      description
        "Packets transmitted delay";
      leaf min {
        type uint32;
        units "microseconds";
        description
          "Min of Packets transmitted delay";
      }
      leaf max {
        type uint32;
        units "microseconds";
        description
          "Max of Packets transmitted delay";
      }
      leaf avg {
        type uint32;
        units "microseconds";
        description
          "Avg of Packets transmitted delay";
      }
    }
    container delay-variation {
      description
        "Packets transmitted delay variation";
      leaf min {
        type uint32;
        units "microseconds";
        description
          "Min of Packets transmitted
           delay variation";
      }
      leaf max {
        type uint32;
        units "microseconds";
        description
          "Max of Packets transmitted
           delay variation";
      }
      leaf avg {
        type uint32;
        units "microseconds";
        description
          "Avg of Packets transmitted
           delay variation";
      }
    }
  }

  grouping stamp-session-percentile {
    description
      "Percentile grouping";
    leaf first-percentile {
      type percentile;
      default "95.00";
      description
        "First percentile to report";
    }
    leaf second-percentile {
      type percentile;
      default "99.00";
      description
        "Second percentile to report";
    }
    leaf third-percentile {
      type percentile;
      default "99.90";
      description
        "Third percentile to report";
    }
  }

  grouping time-percentile-report {
    description
      "Delay percentile report grouping";
    container delay-percentile {
      description
        "Report round-trip, near- and far-end delay";
      leaf rtt-delay {
        type percentile;
        description
          "Percentile of round-trip delay";
      }
      leaf near-end-delay {
        type percentile;
        description
          "Percentile of near-end delay";
      }
      leaf far-end-delay {
        type percentile;
        description
          "Percentile of far-end delay";
      }
    }
    container jitter-percentile {
      description
        "Report round-trip, near- and far-end jitter";
      leaf rtt-jitter {
        type percentile;
        description
          "Percentile of round-trip jitter";
      }
      leaf near-end-jitter {
        type percentile;
        description
          "Percentile of near-end jitter";
      }
      leaf far-end-jitter {
        type percentile;
        description
          "Percentile of far-end jitter";
      }
    }
  }

  grouping packet-loss-statistics {
    description
      "Grouping for Packet Loss statistics";
    container loss {
      description
        "packets transmitted loss";
      leaf loss-count {
        type int32;
        description
          "Number of lost packets
           during the test interval.";
      }
      leaf loss-ratio {
        type percentage;
        description
          "Ratio of packets lost to packets
           sent during the test interval.";
      }
      leaf loss-burst-max {
        type int32;
        description
          "Maximum number of consequtively
           lost packets during the test interval.";
      }
      leaf loss-burst-min {
        type int32;
        description
          "Minimum number of consequtively
           lost packets during the test interval.";
      }
      leaf loss-burst-count {
        type int32;
        description
          "Number of occasions with packet
           loss during the test interval.";
      }
    }
  }

  grouping two-way-metrics {
    description
      "Two-way metrics measured by the Simple TWAMP session";
    container two-way-metrics {
      description
        "two way metrics results of the test session";
      uses delay-statistics;
      uses packet-loss-statistics;
    }
  }

  grouping one-way-metrics {
    description
      "One-way metrics measured or derived for the Simple TWAMP session";
    container one-way-metrics {
      description
        "one way metrics results of the test session";
      uses delay-statistics;
      uses packet-loss-statistics;
    }
  }

  grouping stamp-endpoint-delay-measurement-profile-config {
    description
      "Configuration items for STAMP endpoint delay measurement profile";
    leaf profile-name {
      description
        "The name of the profile.";
      type string {
        length "1..255";
        pattern '[a-zA-Z0-9_-]+';
      }
    }
    /*		leaf dscp-handling-mode {
    type session-dscp-mode;
    default copy-received-value;
    description
    "Session-Reflector handling of DSCP:
    	- use value copied from received TWAMP-Test packet;
    	- use value explicitly configured";
    } */
    leaf dscp-value {
      description
        "The DSCP value for transmitted STAMP packets.";
      type inet:dscp {
        range "0..56";
      }
      default "48";
    }
    leaf packet-padding-mode {
      type padding-fill-mode;
      default "zero";
      description
        "The packet padding mode";
    }
    leaf packet-padding-size {
      type uint32 {
        range "60..1400";
      }
      default "60";
      description
        "Size of the Packet Padding. Suggested to run
         Path MTU Discovery to avoid packet fragmentation
         in IPv4 and packet backholing in IPv6";
    }
    leaf ip-ttl {
      type uint8 {
        range "1..255";
      }
      default "255";
    }
    container ip-performance-thresholds {
      description
        "Contains the thresholds for the measured metrics";
      leaf jitter-egress-max {
        type uint32 {
          range "1..60000000";
        }
        units "microseconds";
        description
          "Maximum source to destination jitter per test (in microseconds)";
      }
      leaf jitter-ingress-max {
        type uint32 {
          range "1..60000000";
        }
        units "microseconds";
        description
          "Maximum destination to source jitter per test (in microseconds)";
      }
      leaf jitter-rtt-max {
        type uint32 {
          range "1..60000000";
        }
        units "microseconds";
        description
          "Maximum jitter per test (in microseconds)";
      }
      leaf delay-rtt-max {
        type uint32 {
          range "1..60000000";
        }
        units "microseconds";
        description
          "Maximum round trip time per test (in microseconds)";
      }
      leaf delay-rtt-min {
        type uint32 {
          range "1..60000000";
        }
        units "microseconds";
        description
          "Minimum round trip time per test (in microseconds)";
      }
      leaf delay-rtt-avg {
        type uint32 {
          range "1..60000000";
        }
        units "microseconds";
        description
          "Average round trip time per test (in microseconds)";
      }
      leaf delay-unidirectional-max {
        type uint32 {
          range "1..60000000";
        }
        units "microseconds";
        description
          "Maximum unidirectional delay time per test (in microseconds)";
      }
      leaf delay-unidirectional-min {
        type uint32 {
          range "1..60000000";
        }
        units "microseconds";
        description
          "Minimum unidirectional delay time per test (in microseconds)";
      }
      leaf delay-unidirectional-avg {
        type uint32 {
          range "1..60000000";
        }
        units "microseconds";
        description
          "Average unidirectional delay time per test (in microseconds)";
      }
      leaf total-loss {
        type uint32 {
          range "1..max";
        }
        description
          "Total probe loss count indicating test failure";
      }
      leaf successive-loss {
        type uint32 {
          range "1..max";
        }
        description
          "Successive probe loss count indicating test failure";
      }
    }
    leaf inform-test-results {
      description
        "Enable or diable the generation of the test failure system event.";
      type admin-state;
      default "disabled";
    }
    choice test-duration {
      description
        "The duration of the test.";
      default "numbered-probes";
      case numbered-probes {
        description
          "Test duration is probe-count times probe-interval.";
        container test-duration-probes {
          leaf probe-count {
            description
              "The number of probes in the test.";
            type uint32 {
              range "1..4294967295";
            }
            default "60";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case time-frame {
        description
          "Test duration is time in minutes (number of probes is derived from the probe-interval).";
        container test-duration-minutes {
          leaf duration {
            description
              "The duration of the test in minutes.";
            type uint32 {
              range "1..4294967295";
            }
            units "minutes";
            default "1";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case non-stop {
        description
          "Test duration is non-stop. Interim results are calculated periodically.";
        container test-duration-nonstop {
          leaf probe-interval {
            description
              "The interval between subsequent probes in the test.";
            type uint8 {
              range "1..255";
            }
            units "seconds";
            default "1";
          }
          leaf computation-interval {
            description
              "Periodic computation interval. Valid for non-stop mode.";
            type uint16 {
              range "1..3600";
            }
            units "seconds";
            default "60";
          }
        }
      }
    }
  }

  grouping stamp-history-stats {
    description
      "Historic statistics of a Simple TWAMP session";
    list history-stats {
      key "index";
      max-elements 1;
      description
        "This list contains the results for the historic
         IP performance tests in a Measurement session ";
      leaf index {
        type uint8;
        description
          "The index number for a specific IP performance test for the Simple TWAMP session";
      }
      leaf start-time {
        type yang:date-and-time;
        mandatory true;
        description
          "The time that the IP performance test started";
      }
      leaf end-time {
        type yang:date-and-time;
        mandatory true;
        description
          "The time that the IP performance test ended";
      }
      leaf test-status {
        type boolean;
        mandatory true;
        description
          "The status of the test";
      }
      // uses stamp-session-parameters;
      uses maintenance-statistics;
      uses two-way-metrics;
      //			uses one-way-metrics;
      container one-way-delay-far-end {
        description
          "one way delay far end of the test session";
        uses delay-statistics;
      }
      container one-way-delay-near-end {
        description
          "one way delay near end of the test session";
        uses delay-statistics;
      }
    }
  }

  grouping icmp-echo-history-stats {
    description
      "Historic statistics of a ICMP echo IP performance measurement session";
    list history-stats {
      key "index";
      max-elements 1;
      description
        "This list contains the results for the historic
         IP performance tests in a Measurement session ";
      leaf index {
        type uint8;
        description
          "The index number for a specific IP performance test for the Simple TWAMP session";
      }
      leaf start-time {
        type yang:date-and-time;
        mandatory true;
        description
          "The time that the IP performance test started";
      }
      leaf end-time {
        type yang:date-and-time;
        mandatory true;
        description
          "The time that the IP performance test ended";
      }
      leaf test-status {
        type boolean;
        mandatory true;
        description
          "The status of the test";
      }
      // uses stamp-session-parameters;
      uses icmp-echo-maintenance-statistics;
      uses two-way-metrics;
    }
  }

  grouping link-performance-dynamic-delay-statistics {
    description
      "Statistics for link performance dynamic delay sessions.";
    container statistics {
      description
        "Contains dynamic delay session statistics";
      container last-advertisement {
        description
          "Contains the statistics last advertised to the dynamic delay consumer";
        leaf last-advertisement-time {
          type yang:date-and-time;
          description
            "The time that the last advertised statistics were reported.";
        }
        leaf last-advertisement-reason {
          type string {
            length "1..255";
          }
          description
            "The reason for the last advertisement.";
        }
        leaf delay-min {
          type uint32;
          units "microseconds";
          description
            "Min of Packets transmitted delay";
        }
        leaf delay-max {
          type uint32;
          units "microseconds";
          description
            "Max of Packets transmitted delay";
        }
        leaf delay-avg {
          type uint32;
          units "microseconds";
          description
            "Avg of Packets transmitted delay";
        }
        leaf jitter-average {
          type uint32;
          units "microseconds";
          description
            "Avg of Packets transmitted
             delay variation";
        }
      }
      container candidate-advertisement {
        description
          "Contains the candidate statistics to be considered for advertisement to the dynamic delay consumer";
        leaf delay-min {
          type uint32;
          units "microseconds";
          description
            "Min of Packets transmitted delay";
        }
        leaf delay-max {
          type uint32;
          units "microseconds";
          description
            "Max of Packets transmitted delay";
        }
        leaf delay-avg {
          type uint32;
          units "microseconds";
          description
            "Avg of Packets transmitted delay";
        }
        leaf jitter-average {
          type uint32;
          units "microseconds";
          description
            "Avg of Packets transmitted
             delay variation";
        }
        leaf delay-rolling-avg {
          type uint32;
          units "microseconds";
          description
            "Rolling avg of Packets transmitted delay";
        }
      }
    }
  }

  grouping stamp-session-sender-instance-config {
    description
      "Configuration items for Simple TWAMP Session-Sender sessions";
    leaf session-name {
      type string {
        length "1..255";
      }
      description
        "Session name";
    }
    /*		leaf session-description {
    description
    "Session description";
    type string {
    length "1..255";
    }
    } */
    leaf admin-state {
      type admin-state;
      default "disabled";
      description
        "The administrative state of the Simple TWAMP test-session";
    }
    leaf profile {
      type leafref {
        path "../../../../profiles/endpoint-delay-measurement-profiles/profile/profile-name";
      }
      default "default";
      description
        "The Simple TWAMP profile containing session parameters configuration";
    }
  }

  grouping stamp-session-sender-instance-oper {
    description
      "Operational items for Simple TWAMP Session-Sender";
    /*		leaf sender-session-state {
    type enumeration {
    enum active {
    	description 
    		"Test session is active";
    }
    enum ready {
    	description 
    		"Test session is idle";
    }
    }
    description
    "State of the particular Simple TWAMP test
    session at the sender";
    } */
    leaf sender-udp-port {
      type inet:port-number;
      mandatory true;
      description
        "The UDP port number allocated for the session by the local Simple TWAMP Session-Sender";
    }
    leaf reflector-udp-port {
      type inet:port-number;
      mandatory true;
      description
        "The UDP port number of the remote Simple TWAMP Session-Reflector";
    }
    leaf session-uptime {
      type yang:timeticks;
      description
        "Uptime of the Simple TWAMP session";
      mandatory true;
    }
    leaf number-of-packets {
      type uint32;
      description
        "The overall number of UDP test packets to be
         transmitted by the sender for this test session";
    }
    leaf packet-padding-size {
      type uint32;
      description
        "Size of the Packet Padding. Suggested to run
         Path MTU Discovery to avoid packet fragmentation
         in IPv4 and packet blackholing in IPv6";
    }
    leaf interval {
      type uint32;
      units "microseconds";
      description
        "Time interval between transmission of two
         consecutive packets in the test session";
    }
    leaf dscp {
      type inet:dscp;
      description
        "The DSCP value that was placed in the header of
         TWAMP UDP test packets by the Session-Sender.";
    }
    /*		container current-stats {
    description
    "This container contains the results for the current
    Measurement Interval in a Measurement session ";
    leaf start-time {
    type yang:date-and-time;
    mandatory true;
    description
    	"The time that the current Measurement Interval started";
    }
    
    leaf packet-padding-size {
    type uint32;
    default 27;
    description
    	"Size of the Packet Padding. Suggested to run
    	Path MTU Discovery to avoid packet fragmentation
    	in IPv4 and packet backholing in IPv6";
    }
    
    leaf interval  {
    type uint32;
    units microseconds;
    description
    	"Time interval between transmission of two
    	consecutive packets in the test session";
    }
    
    // uses stamp-session-parameters;
    
    leaf dscp {
    type inet:dscp;
    description
    	"The DSCP value that was placed in the header of
    	TWAMP UDP test packets by the Session-Sender.";
    }
    
    uses maintenance-statistics;
    
    container two-way-delay {
    description
    	"two way delay result of the test session";
    uses delay-statistics;
    }
    
    container one-way-delay-far-end {
    description
    	"one way delay far-end of the test session";
    uses delay-statistics;
    }
    
    container one-way-delay-near-end {
    description
    	"one way delay near-end of the test session";
    uses delay-statistics;
    }
    
    container low-percentile {
    when "/dn-top:drivenets-top/dn-srv:services/dn-srv-stamp:simple-twamp/"
    +"dn-srv-stamp:stamp-session-sender/dn-srv-stamp:sessions/"
    +"dn-srv-stamp:test-session[session-id]/dn-srv-stamp:config-items/dn-srv-stamp:first-percentile != '0.00'" {
    	description
    		"Only valid if the
    		the first-percentile is not NULL";
    }
    description
    	"Low percentile report";
    uses time-percentile-report;
    }
    
    container mid-percentile {
    when "/dn-top:drivenets-top/dn-srv:services/dn-srv-stamp:simple-twamp/"
    +"dn-srv-stamp:stamp-session-sender/dn-srv-stamp:sessions/"
    +"dn-srv-stamp:test-session[session-id]/dn-srv-stamp:config-items/dn-srv-stamp:second-percentile != '0.00'" {
    	description
    		"Only valid if the
    		the first-percentile is not NULL";
    }
    description
    	"Mid percentile report";
    uses time-percentile-report;
    }
    
    container high-percentile {
    when "/dn-top:drivenets-top/dn-srv:services/dn-srv-stamp:simple-twamp/"
    +"dn-srv-stamp:stamp-session-sender/dn-srv-stamp:sessions/"
    +"dn-srv-stamp:test-session[session-id]/dn-srv-stamp:config-items/dn-srv-stamp:third-percentile != '0.00'" {
    	description
    		"Only valid if the
    		the first-percentile is not NULL";
    }
    description
    	"High percentile report";
    uses time-percentile-report;
    }
    
    container two-way-loss {
    description
    	"two way loss count and ratio result of
    	the test session";
    uses packet-loss-statistics;
    }
    
    container one-way-loss-far-end {
    when "/dn-top:drivenets-top/dn-srv:services/dn-srv-stamp:simple-twamp/"
    +"dn-srv-stamp:stamp-session-reflector/dn-srv-stamp:config-items/"
    +"dn-srv-stamp:reflector-mode = 'stateful'" {
    	description
    		"One-way statistic is only valid if the
    		session-reflector is in stateful mode.";
    }
    description
    	"one way loss count and ratio far-end of
    	the test session";
    uses packet-loss-statistics;
    }
    
    container one-way-loss-near-end {
    when "/dn-top:drivenets-top/dn-srv:services/dn-srv-stamp:simple-twamp/"
    +"dn-srv-stamp:stamp-session-reflector/dn-srv-stamp:config-items/"
    +"dn-srv-stamp:reflector-mode = 'stateful'" {
    	description
    		"One-way statistic is only valid if the
    		session-reflector is in stateful mode.";
    }
    description
    	"one way loss count and ratio near-end of
    	the test session";
    uses packet-loss-statistics;
    }
    
    } */
    leaf ongoing-start-time {
      type yang:date-and-time;
      mandatory true;
      description
        "The time that the IP performance test started";
    }
    leaf ongoing-expected-end-time {
      type yang:date-and-time;
      mandatory true;
      description
        "The time that the IP performance test is expected to end";
    }
    uses stamp-history-stats;
  }

  grouping icmp-echo-profile-config {
    description
      "Configuration items for ICMP echo performance measurement profile";
    leaf profile-name {
      description
        "The name of the profile.";
      type string {
        length "1..255";
        pattern '[a-zA-Z0-9_-]+';
      }
    }
    /*		leaf dscp-handling-mode {
    type session-dscp-mode;
    default copy-received-value;
    description
    "Session-Reflector handling of DSCP:
    	- use value copied from received TWAMP-Test packet;
    	- use value explicitly configured";
    } */
    leaf dscp-value {
      description
        "The DSCP value for transmitted packets.";
      type inet:dscp {
        range "0..56";
      }
      default "48";
    }
    leaf packet-padding-mode {
      type padding-fill-mode;
      default "zero";
      description
        "The packet padding mode";
    }
    leaf data-size {
      type uint32 {
        range "64..1400";
      }
      default "64";
      description
        "Size of the Packet Payload. Suggested to run
         Path MTU Discovery to avoid packet fragmentation
         in IPv4 and packet backholing in IPv6";
    }
    leaf ip-ttl {
      type uint8 {
        range "1..255";
      }
      default "255";
    }
    container ip-performance-thresholds {
      description
        "Contains the thresholds for the measured metrics";
      leaf jitter-rtt-max {
        type uint32 {
          range "1..60000000";
        }
        units "microseconds";
        description
          "Maximum jitter per test (in microseconds)";
      }
      leaf delay-rtt-max {
        type uint32 {
          range "1..60000000";
        }
        units "microseconds";
        description
          "Maximum round trip time per test (in microseconds)";
      }
      leaf delay-rtt-min {
        type uint32 {
          range "1..60000000";
        }
        units "microseconds";
        description
          "Minimum round trip time per test (in microseconds)";
      }
      leaf delay-rtt-avg {
        type uint32 {
          range "1..60000000";
        }
        units "microseconds";
        description
          "Average round trip time per test (in microseconds)";
      }
      leaf total-loss {
        type uint32 {
          range "1..max";
        }
        description
          "Total probe loss count indicating test failure";
      }
      leaf successive-loss {
        type uint32 {
          range "1..max";
        }
        description
          "Successive probe loss count indicating test failure";
      }
    }
    leaf inform-test-results {
      description
        "Enable or diable the generation of the test failure system event.";
      type admin-state;
      default "disabled";
    }
    choice test-duration {
      description
        "The duration of the test.";
      default "numbered-probes";
      case numbered-probes {
        description
          "Test duration is probe-count times probe-interval.";
        container test-duration-probes {
          leaf probe-count {
            description
              "The number of probes in the test.";
            type uint32 {
              range "1..4294967295";
            }
            default "60";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case time-frame {
        description
          "Test duration is time in minutes (number of probes is derived from the probe-interval).";
        container test-duration-minutes {
          leaf duration {
            description
              "The duration of the test in minutes.";
            type uint32 {
              range "1..4294967295";
            }
            units "minutes";
            default "1";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case non-stop {
        description
          "Test duration is non-stop. Interim results are calculated periodically.";
        container test-duration-nonstop {
          leaf probe-interval {
            description
              "The interval between subsequent probes in the test.";
            type uint8 {
              range "1..255";
            }
            units "seconds";
            default "1";
          }
          leaf computation-interval {
            description
              "Periodic computation interval. Valid for non-stop mode.";
            type uint16 {
              range "1..3600";
            }
            units "seconds";
            default "60";
          }
        }
      }
    }
  }

  grouping icmp-echo-session-sender-instance-config {
    description
      "Configuration items for originated ICMP echo IP perforamnce measurement sessions";
    leaf session-name {
      type string {
        length "1..255";
      }
      description
        "Session name";
    }
    leaf admin-state {
      type admin-state;
      default "disabled";
      description
        "The administrative state of the ICMP echo IP perforamnce measurement test-session";
    }
    leaf profile {
      type leafref {
        path "../../../../profiles/icmp-echo-ip-performance-measurement-profiles/profile/profile-name";
      }
      default "default";
      description
        "The ICMP echo IP perforamnce measurement profile containing session parameters configuration";
    }
    leaf source-ip {
      type inet:ip-address;
      mandatory true;
      description
        "Sender IP address";
    }
    leaf destination-ip {
      type inet:ip-address;
      mandatory true;
      description
        "Target IP address";
    }
    leaf destination-vrf {
      type leafref {
        path "/dn-top:drivenets-top/dn-network-services:network-services/dn-vrf:vrfs/dn-vrf:vrf/dn-vrf:vrf-name";
      }
      default "default";
      must "((current() != 'mgmt0') and (current() != 'mgmt-ncc-0') and (current() != 'mgmt-ncc-1'))";
      description
        "Target VRF";
    }
  }

  grouping icmp-echo-session-sender-instance-oper {
    description
      "Operational items for originated ICMP echo IP performance measurement test sessions";
    leaf session-identifier {
      type uint32;
      description
        "The ICMP identifier field of the ICMP echo IP performance measurement test session";
      mandatory true;
    }
    leaf session-uptime {
      type yang:timeticks;
      description
        "Uptime of the ICMP echo IP performance measurement test session";
      mandatory true;
    }
    leaf number-of-packets {
      type uint32;
      description
        "The overall number of test packets to be
         transmitted by the sender for this test session";
    }
    leaf data-size {
      type uint32;
      description
        "Size of the Packet Payload. Suggested to run
         Path MTU Discovery to avoid packet fragmentation
         in IPv4 and packet blackholing in IPv6";
    }
    leaf interval {
      type uint32;
      units "microseconds";
      description
        "Time interval between transmission of two
         consecutive packets in the test session";
    }
    leaf dscp {
      type inet:dscp;
      description
        "The DSCP value that was placed in the header of
         ICMP echo test packets by the Session-Sender.";
    }
    leaf ongoing-start-time {
      type yang:date-and-time;
      mandatory true;
      description
        "The time that the IP performance test started";
    }
    leaf ongoing-expected-end-time {
      type yang:date-and-time;
      mandatory true;
      description
        "The time that the IP performance test is expected to end";
    }
    uses icmp-echo-history-stats;
  }

  grouping cfm-two-way-delay-measurement-profile-config {
    description
      "Configuration items for CFM two-way delay measurement profile";
    leaf profile-name {
      description
        "The name of the profile.";
      type string {
        length "1..255";
        pattern '[a-zA-Z0-9_-]+';
      }
    }
    container cfm-eth-dm-performance-thresholds {
      description
        "Contains the thresholds for the measured metrics";
      leaf delay-rtt-min {
        type uint32 {
          range "1..60000000";
        }
        units "microseconds";
        description
          "Minimum round trip time per test (in microseconds)";
      }
      leaf delay-rtt-avg {
        type uint32 {
          range "1..60000000";
        }
        units "microseconds";
        description
          "Average round trip time per test (in microseconds)";
      }
      leaf delay-rtt-max {
        type uint32 {
          range "1..60000000";
        }
        units "microseconds";
        description
          "Maximum round trip time per test (in microseconds)";
      }
      leaf jitter-rtt-avg {
        type uint32 {
          range "1..60000000";
        }
        units "microseconds";
        description
          "Average round trip jitter per test (in microseconds)";
      }
      leaf jitter-rtt-max {
        type uint32 {
          range "1..60000000";
        }
        units "microseconds";
        description
          "Maximum round trip jitter per test (in microseconds)";
      }
      leaf success-rate-percent {
        type percentage {
          range "0.0..100.0";
        }
        units "percent";
        description
          "Success rate percentage";
      }
    }
    leaf inform-test-results {
      description
        "Enable or disable the generation of the test failure system event.";
      type admin-state;
      default "disabled";
    }
    choice test-duration {
      description
        "The duration of the test.";
      default "numbered-probes";
      case numbered-probes {
        description
          "Test duration is probe-count times probe-interval.";
        container test-duration-probes {
          leaf probe-count {
            description
              "The number of probes in the test.";
            type uint32 {
              range "1..4294967295";
            }
            default "60";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case time-frame {
        description
          "Test duration is time in minutes (number of probes is derived from the probe-interval).";
        container test-duration-minutes {
          leaf duration {
            description
              "The duration of the test in minutes.";
            type uint32 {
              range "1..4294967295";
            }
            units "minutes";
            default "1";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case non-stop {
        description
          "Test duration is non-stop. Interim results are calculated periodically.";
        container test-duration-nonstop {
          leaf probe-interval {
            description
              "The interval between subsequent probes in the test.";
            type uint8 {
              range "1..255";
            }
            units "seconds";
            default "1";
          }
          leaf computation-interval {
            description
              "Periodic computation interval. Valid for non-stop mode.";
            type uint16 {
              range "1..3600";
            }
            units "seconds";
            default "60";
          }
        }
      }
    }
  }

  grouping cfm-two-way-synthetic-loss-measurement-profile-config {
    description
      "Configuration items for CFM two-way synthetic loss measurement profile";
    leaf profile-name {
      description
        "The name of the profile.";
      type string {
        length "1..255";
        pattern '[a-zA-Z0-9_-]+';
      }
    }
    container cfm-eth-sl-performance-thresholds {
      description
        "Contains the thresholds for the measured metrics";
      leaf near-end-loss {
        type percentage {
          range "0.0..100.0";
        }
        units "percent";
        description
          "Near-end loss threshold in percentage";
      }
      leaf far-end-loss {
        type percentage {
          range "0.0..100.0";
        }
        units "percent";
        description
          "Far-end loss threshold in percentage";
      }
    }
    leaf pcp {
      description
        "PCP value to be used for the test";
      type uint8 {
        range "0..7";
      }
      default "0";
    }
    leaf inform-test-results {
      description
        "Enable or disable the generation of the test failure system event.";
      type admin-state;
      default "disabled";
    }
    choice test-duration {
      description
        "The duration of the test.";
      default "numbered-probes";
      case numbered-probes {
        description
          "Test duration is probe-count times probe-interval.";
        container test-duration-probes {
          leaf probe-count {
            description
              "The number of probes in the test.";
            type uint32 {
              range "1..4294967295";
            }
            default "60";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case time-frame {
        description
          "Test duration is time in minutes (number of probes is derived from the probe-interval).";
        container test-duration-minutes {
          leaf duration {
            description
              "The duration of the test in minutes.";
            type uint32 {
              range "1..4294967295";
            }
            units "minutes";
            default "1";
          }
          leaf probe-interval {
            description
              "The interval between subsequent probes in the test.";
            type uint8 {
              range "1..255";
            }
            units "seconds";
            default "1";
          }
          leaf repeat-interval {
            description
              "The interval between subsequent tests.";
            type uint32 {
              range "1..4294967295";
            }
            units "seconds";
            default "60";
          }
        }
      }
      case non-stop {
        description
          "Test duration is non-stop. Interim results are calculated periodically.";
        container test-duration-nonstop {
          leaf probe-interval {
            description
              "The interval between subsequent probes in the test.";
            type uint8 {
              range "1..255";
            }
            units "seconds";
            default "1";
          }
          leaf computation-interval {
            description
              "Periodic computation interval. Valid for non-stop mode.";
            type uint16 {
              range "1..3600";
            }
            units "seconds";
            default "60";
          }
        }
      }
    }
  }

  grouping performance-monitoring-top {
    container performance-monitoring {
      description
        "Performance Monitoring.";
      container interfaces {
        description
          "Interfaces to be monitored.";
        list interface {
          key "interface-name";
          description
            "The list of interfaces.";
          leaf interface-name {
            type leafref {
              path "../config-items/interface-name";
            }
            description
              "The name of the interface -- used to address the interface.";
          }
          container config-items {
            description
              "Interface Performance Monitoring configuration items";
            uses performance-monitoring-config;
          }
          container oper-items {
            config false;
            description
              "Interface Performance Monitoring operational items";
            uses performance-monitoring-config;
          }
          uses dn-group:apply-group;
        }
      }
      container stamp-sessions {
        description
          "STAMP Sender Sessions";
        list test-session {
          key "session-name";
          //					unique "source-ip destination-ip destination-vrf";
          description
            "This structure is a container of test session
             managed objects";
          leaf session-name {
            type leafref {
              path "../config-items/session-name";
            }
          }
          /*					leaf source-ip {
          type leafref {
          path "../config-items/source-ip";
          }
          }
          
          leaf sender-udp-port {
          type leafref {
          path "../config-items/sender-udp-port";
          }
          }
          
          leaf destination-ip {
          type leafref {
          path "../config-items/destination-ip";
          }
          }
          
          leaf destination-vrf {
          type leafref {
          path "../config-items/destination-vrf";
          }
          }
          
          leaf reflector-udp-port {
          type leafref {
          path "../config-items/reflector-udp-port";
          }
          } */
          container config-items {
            description
              "Holds configuration data";
            uses stamp-session-sender-instance-config;
            uses stamp-session-parameters;
            // uses stamp-session-percentile;
          }
          container oper-items {
            config false;
            description
              "Holds state data";
            uses stamp-session-sender-instance-config;
            uses stamp-session-parameters;
            uses stamp-session-sender-instance-oper;
            // uses stamp-session-percentile;
          }
          uses dn-group:apply-group;
        }
      }
      container icmp-echo-sessions {
        description
          "ICMP echo IP performance measurement sessions";
        list test-session {
          max-elements 5000;
          key "session-name";
          //					unique "source-ip destination-ip destination-vrf";
          description
            "This structure is a container of test session
             managed objects";
          leaf session-name {
            type leafref {
              path "../config-items/session-name";
            }
          }
          container config-items {
            description
              "Holds configuration data";
            uses icmp-echo-session-sender-instance-config;
          }
          container oper-items {
            config false;
            description
              "Holds state data";
            uses icmp-echo-session-sender-instance-config;
            uses icmp-echo-session-sender-instance-oper;
          }
          uses dn-group:apply-group;
        }
      }
      container cfm-tests {
        description
          "CFM performance monitoring test results";
      }
      container profiles {
        description
          "Performance monitoring profiles";
        container link-delay-measurement-profiles {
          description
            "Contains link delay measurement profiles.";
          list profile {
            description
              "The list of STAMP link-performance profiles that can be attached to a session";
            key "profile-name";
            max-elements 5;
            leaf profile-name {
              type leafref {
                path "../config-items/profile-name";
              }
              description
                "The profile name. The profile is attached to a Simple TWAMP session";
            }
            container config-items {
              description
                "Configuration data for STAMP link-performance profile";
              uses stamp-link-performance-profile-config;
            }
            container oper-items {
              config false;
              description
                "State variables for STAMP link-performance profile";
              uses stamp-link-performance-profile-config;
            }
            uses dn-group:apply-group;
          }
        }
        container endpoint-delay-measurement-profiles {
          description
            "Contains endpoint delay measurement profiles.";
          list profile {
            description
              "The list of STAMP endpoint measurement profiles that can be attached to a session";
            key "profile-name";
            max-elements 5;
            leaf profile-name {
              type leafref {
                path "../config-items/profile-name";
              }
              description
                "The profile name. The profile is attached to a Simple TWAMP session";
            }
            container config-items {
              description
                "Configuration data for STAMP endpoint delay measurement profile";
              uses stamp-endpoint-delay-measurement-profile-config;
            }
            container oper-items {
              config false;
              description
                "State variables for STAMP endpoint delay measurement profile";
              uses stamp-endpoint-delay-measurement-profile-config;
            }
            uses dn-group:apply-group;
          }
        }
        container icmp-echo-ip-performance-measurement-profiles {
          description
            "Contains ICMP echo IP performance measurement profiles";
          list profile {
            description
              "Contains the list of ICMP echo IP perforamnce measurement profiles that can be attached to a session";
            key "profile-name";
            max-elements 5;
            leaf profile-name {
              type leafref {
                path "../config-items/profile-name";
              }
              description
                "The profile name. The profile is attached to a ICMP echo IP performance measurement session";
            }
            container config-items {
              description
                "Configuration data for ICMP echo IP performance measurement profile";
              uses icmp-echo-profile-config;
            }
            container oper-items {
              config false;
              description
                "State variables for ICMP echo IP performance measurement profile";
              uses icmp-echo-profile-config;
            }
            uses dn-group:apply-group;
          }
        }
        container cfm {
          description
            "Contains CFM performance monitoring profiles";
          container two-way-delay-measurement {
            description
              "Contains CFM two-way delay measurement profiles";
            list profile {
              description
                "The list of CFM two-way delay measurement profiles that can be attached to a CFM test";
              key "profile-name";
              max-elements 5;
              leaf profile-name {
                type leafref {
                  path "../config-items/profile-name";
                }
                description
                  "The profile name. The profile is attached to a CFM two-way delay measurement test";
              }
              container config-items {
                description
                  "Configuration data for CFM two-way delay measurement profile";
                uses cfm-two-way-delay-measurement-profile-config;
              }
              container oper-items {
                config false;
                description
                  "State variables for CFM two-way delay measurement profile";
                uses cfm-two-way-delay-measurement-profile-config;
              }
              uses dn-group:apply-group;
            }
          }
          container two-way-synthetic-loss-measurement {
            description
              "Contains CFM two-way synthetic loss measurement profiles";
            list profile {
              description
                "The list of CFM two-way synthetic loss measurement profiles that can be attached to a CFM test";
              key "profile-name";
              max-elements 5;
              leaf profile-name {
                type leafref {
                  path "../config-items/profile-name";
                }
                description
                  "The profile name. The profile is attached to a CFM two-way synthetic loss measurement test";
              }
              container config-items {
                description
                  "Configuration data for CFM two-way synthetic loss measurement profile";
                uses cfm-two-way-synthetic-loss-measurement-profile-config;
              }
              container oper-items {
                config false;
                description
                  "State variables for CFM two-way synthetic loss measurement profile";
                uses cfm-two-way-synthetic-loss-measurement-profile-config;
              }
              uses dn-group:apply-group;
            }
          }
        }
      }
    }
  }

  // augment statements

  augment "/dn-top:drivenets-top/dn-services:services" {
    description
      "Adds performance-monitoring configuration to top model";
    uses performance-monitoring-top;
  }

  augment "/dn-top:drivenets-top/dn-services:services/dn-pm:performance-monitoring/dn-pm:interfaces/"
        + "dn-pm:interface/dn-pm:oper-items/dn-pm:delay-measurement/dn-pm:link-delay-measurement" {
    description
      "Adds STAMP session statistics to dynamic link delay measurement sessions oper items";
    uses link-performance-dynamic-delay-statistics;
  }
}
